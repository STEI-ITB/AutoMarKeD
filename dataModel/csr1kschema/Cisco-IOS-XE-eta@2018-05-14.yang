module Cisco-IOS-XE-eta {
  namespace "http://cisco.com/ns/yang/Cisco-IOS-XE-eta";
  prefix ios-eta;

  import ietf-inet-types {
    prefix inet;
  }


  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Encrypted Traffic Analytics Yang model.
     Copyright (c) 2017-2018 by Cisco Systems, Inc.
     All rights reserved.";

  // =========================================================================
  // REVISION
  // =========================================================================
  revision 2018-05-14 {
    description
      "Limit string lengths for threat-defense features";
  }

  revision 2018-02-22 {
    description
      "Add threat-defense support for Ethernet interfaces";
  }

  revision 2017-11-27 {
    description
      "Added Change 25GE name";
  }

  revision 2017-11-14 {
    description
      "Add 100GE interface support";
  }

  revision 2017-10-16 {
    description
      "Initial revision";
  }

  grouping config-eta-grouping {
    container et-analytics {
      description
        "Encrypted Traffic Analytics";
      presence true; 

      // et-analytics / ip flow-export destination *
      container ip {
        description
          "Specify netflow record export destination ip address and port";
        container flow-export {
          description
            "netflow record export";
          list destination {
            description
              "netflow record export destination";
            key "address port";
            leaf address {
              type inet:ipv4-address;
            }
            leaf port {
              type uint16 {
                range "1..65535";
              }
            }
          }
          container destination-vrf {
            list destination {
              description
                "netflow record export destination";
              key "address port vrf";
              leaf address {
                type inet:ipv4-address;
              }
              leaf port {
                type uint16 {
                  range "1..65535";
                }
              }
              leaf vrf {
                description
                  "Optional VRF label";
                type string {
                  length "1..32";
                }
              }
            }
          }
        }
      }

      // et-analytics / inactive-timeout
      leaf inactive-timeout {
        description
          "Specify Inactive flow timeout value";
        type uint32 {
          range "1..604800";
        }
      }

      // et-analytics / whitelist acl
      container whitelist {
        description
          "Whitelist traffic";
        leaf acl {
          description
            "Access list";
          type union {
            type uint16 {
              range "1..199 | 1300..2699";
            }
            type string {
              length "1..64";
            }
          }
        }
      }
    }
  }

  grouping config-interface-eta-grouping {
    // interface * / et-analytics
    container et-analytics {
      description
        "et-analytics support on this interface";
      leaf enable {
        description
          "Enable et-analytics on this interface";
        type empty;
      }
    }
  }

  /////////////////////////////////////////////////////////
  // native / et-analytics
  /////////////////////////////////////////////////////////
  augment "/ios:native" {
    uses config-eta-grouping;
  } //augment

  /////////////////////////////////////////////////////////
  // native / interface
  /////////////////////////////////////////////////////////
  augment "/ios:native/ios:interface/ios:Ethernet" {
    uses config-interface-eta-grouping;
  }

  augment "/ios:native/ios:interface/ios:FastEthernet" {
    uses config-interface-eta-grouping;
  }

  augment "/ios:native/ios:interface/ios:GigabitEthernet" {
    uses config-interface-eta-grouping;
  }

  augment "/ios:native/ios:interface/ios:TenGigabitEthernet" {
    uses config-interface-eta-grouping;
  }

  augment "/ios:native/ios:interface/ios:FiveGigabitEthernet" {
    uses config-interface-eta-grouping;
  }

  augment "/ios:native/ios:interface/ios:TwentyFiveGigE" {
    uses config-interface-eta-grouping;
  }

  augment "/ios:native/ios:interface/ios:FortyGigabitEthernet" {
    uses config-interface-eta-grouping;
  }

  augment "/ios:native/ios:interface/ios:HundredGigE" {
    uses config-interface-eta-grouping;
  }

  augment "/ios:native/ios:interface/ios:TwoGigabitEthernet" {
    uses config-interface-eta-grouping;
  }

  augment "/ios:native/ios:interface/ios:LISP" {
    uses config-interface-eta-grouping;
  }

  augment "/ios:native/ios:interface/ios:Loopback" {
    uses config-interface-eta-grouping;
  }

  augment "/ios:native/ios:interface/ios:Tunnel" {
    uses config-interface-eta-grouping;
  }

  augment "/ios:native/ios:interface/ios:Virtual-Template" {
    uses config-interface-eta-grouping;
  }

  augment "/ios:native/ios:interface/ios:Vlan" {
    uses config-interface-eta-grouping;
  }

  augment "/ios:native/ios:interface/ios:vasileft" {
    uses config-interface-eta-grouping;
  }

  augment "/ios:native/ios:interface/ios:vasiright" {
    uses config-interface-eta-grouping;
  }

} //module
