module Cisco-IOS-XE-bgp {
  namespace "http://cisco.com/ns/yang/Cisco-IOS-XE-bgp";
  prefix ios-bgp;

  import ietf-inet-types {
    prefix inet;
  }


  import Cisco-IOS-XE-types {
    prefix ios-types;
  }

  import Cisco-IOS-XE-features {
    prefix ios-features;
  }

  import Cisco-IOS-XE-interface-common {
    prefix ios-ifc;
  }
  import Cisco-IOS-XE-ospf {
    prefix ios-ospf;
  }
  import Cisco-IOS-XE-ospfv3 {
    prefix ios-ospfv3;
  }
  import Cisco-IOS-XE-native {
    prefix ios;
  }

  organization
    "Cisco Systems, Inc.";

  contact
    "Cisco Systems, Inc.
     Customer Service

     Postal: 170 W Tasman Drive
     San Jose, CA 95134

     Tel: +1 1800 553-NETS

     E-mail: cs-yang@cisco.com";

  description
    "Cisco XE Native Border Gateway Protocol (BGP) Yang model.
     Copyright (c) 2017-2018 by Cisco Systems, Inc.
     All rights reserved.";

  // =========================================================================
  // REVISION
  // =========================================================================
  revision 2018-06-26 {
    description
      "Fix for router-id vrf value, vrf neighbor configuration,
      address-family deletion, and remove vrf auto-summary";
  }
  revision 2018-06-08 {
    description
      "Create new groupings for global, af, and neighbor scopes in order to
      remove invalid leaves present in model";
  }
  revision 2018-06-07 {
    description
      "Added bgp router-id interface";
  }
  revision 2018-05-21 {
    description
      "change redistribute router id to type leaflef under router bgp address-family";
  }
  revision 2018-05-15 {
    description
      "fix send-community, fall-over, redistribute, max-paths, backdoor,
      log-neighbor-changes, and network/mask errors";
  }
  revision 2018-05-01 {
    description
      "restructure BGP neighbor and peer-group";
  }
  revision 2018-04-02 {
    description
      "Some more Evpn cli added";
  }
  revision 2018-03-15 {
    description
      "Evpn cli for bgp added";
  }
  revision 2018-02-01 {
    description
      "support multiple aggregate-address for both ipv4 and ipv6";
  }
  revision 2018-01-26 {
    description
      "fix config issue -redistribute OSPF under bgp process";
  }
  revision 2018-01-10 {
    description
      "fix bgp bestpath med missing-as-worst";
  }
  revision 2017-11-09 {
    description
      "fix aggregate-address cli generation issue";
  }
  revision 2017-09-18 {
    description
      "BGP neighbor should match a v4/v6 address";
  }
  revision 2017-09-08 {
    description
      "Add show no for enhanced-error";
  }
  revision 2017-08-17 {
    description
      "send-community delete before change";
  }
  revision 2017-08-10 {
    description
      "Add bgp mpls-local-label, import path selection all, bgp bestpath as-path ignore";
  }
  revision 2017-08-02 {
    description
      "Fix delete for redistribute connected";
  }
  revision 2017-07-30 {
    description
      "adding neighbor remove-private-as support";
  }
  revision 2017-07-27 {
    description
      "Fix delete for redistribute connected";
  }
  revision 2017-07-17 {
    description
      "adding neighbor send-label";
  }
  revision 2017-07-10 {
    description
      "adding redistribute ospfv3";
  }
  revision 2017-05-25 {
    description
      "adding neighbor listen and next-hop-self all";
  }
  revision 2017-04-28 {
    description
      "inet:ipv6-prefix changed to ios-types:ipv6-prefix";
  }
  revision 2017-03-02 {
    description
      "NED extension - add version4 for bgp template peer-session";
  }
  revision 2017-02-08 {
    description
      "NED extension - router bgp address-family options - 
                   soo, max paths, import path";
  }
  revision 2017-02-07 {
    description
      "Initial revision";
  }

  // router bgp * / bgp router-id
  grouping bgp-router-id-grouping {
    container router-id {
      description
	"Override configured router identifier (peers will reset)";
      choice id-choice {
	leaf ip-id {
	  description
	    "Manually configured router identifier";
	  type inet:ipv4-address;
	}
	container interface {
	  description
	    "Use IPv4 address on interface";
	  uses ios-ifc:interface-grouping;
	}
	leaf vrf {
	  description
	    "vrf-specific router id configuration";
	  type enumeration {
	    enum "auto-assign";
	  }
        }
      }
    }
  }
    
  grouping global-bgp-grouping {
    description
      "BGP specific commands";
    // router bgp * / bgp aigp-rib-metric
    leaf aigp-rib-metric {
      description 
        "Install RIB metric as NH metric + metric on AIGP attribute";
      type empty;
    }
    
    // router bgp * / bgp always-compare-med
    leaf always-compare-med {
      description
        "Allow comparing MED from different neighbors";
      type empty;
    }
    
    // router bgp * / bgp asnotation
    container asnotation {
      description "Change the default AS plain notation";
      leaf dot {
        description "AS dot notation";
        type empty;
      }
    }
    
    // router bgp * / bgp bestpath
    container bestpath {
      description
        "Change the default bestpath selection";
      leaf as-path {
        type enumeration {
          enum "ignore";
        }
      }
      leaf compare-routerid {
        type empty;
      }
      container cost-community {
        description
          "cost community";
        leaf ignore {
          description
            "Ignore cost communities in bestpath selection";
          type empty;
        }
      }
      container igp-metric {
        description
          "igp metric";
        leaf ignore {
          description
            "Ignore igp metric in bestpath selection";
          type empty;
        }
      }
      container med {
        description
          "MED attribute";
        choice med-choice {
          container confed {
            description
              "Compare MED among confederation paths";
            presence "Compare MED among confederation paths";
            leaf missing-as-worst {
              description
                "Treat missing MED as the least preferred one";
              type empty;
            }
          }
          leaf missing-as-worst {
            description
              "Treat missing MED as the least preferred one";
            type empty;
          }
        }
      }
    }
    
    // router bgp * / bgp client-to-client
    container client-to-client {
      description
        "Configure client to client route reflection";
      leaf reflection {
        description
          "reflection of routes allowed";
	type boolean;
      }
    }
    
    // router bgp * / bgp cluster-id
    leaf cluster-id {
      type union {
        type uint32 {
          range "1..4294967295";
        }
        type inet:ipv4-address;
      }
    }
    
    // router bgp * / bgp confederation
    container confederation {
      description
        "AS confederation parameters";
      leaf identifier {
        type inet:as-number;
      }
      container peers {
        description
          "Peer ASs in BGP confederation";
        leaf-list peers-as {
          type inet:as-number;
        }
      }
    }

    // router bgp * / bgp consistency-checker
    container consistency-checker {
      description
        "Consistency-checker";
      container auto-repair {
        description
          "Auto-Repair";
        presence "true";
        leaf interval {
          description
            "Interval (minutes)";
          type uint16 {
            range "5..1440";
          }
        }
      }
      container error-message {
        description
          "Log Error-Msg";
        presence "true";
        leaf interval {
          description
            "Interval (minutes)";
          type uint16 {
            range "5..1440";
          }
        }
      }
    }

    // router bgp * / bgp default
    container default {
      description
        "Configure BGP defaults";
      leaf ipv4-unicast {
	description
	  "Activate ipv4-unicast for a peer by default";
	type boolean;
      }
      leaf ipv6-nexthop {
	description
	  "Default IPv6 nexthop format";
	type boolean;
      }
      leaf local-preference {
	description
	  "local preference (higher=more preferred)";
	default "100";
	type uint32 {
	  range "1..4294967295";
	}
      }
      leaf route-target {
	description
	  "Control behavior based on Route-Target attributes";
	default "filter";
	type enumeration {
	  enum "filter";
	}
      }
    }

    // router bgp * / bgp deterministic-med
    leaf deterministic-med {
      description
        "Pick the best-MED path among paths advertised from the neighboring AS";
      type empty;
    }

    // router bgp * / bgp dynamic-med-interval
    container dynamic-med-interval {
      description
        "Set the interval to re-compute dynamic MED from IGP metric";
      leaf interval {
        description
          "Interval value (seconds)";
        type uint32 {
          range "60..4294967295";
        }
      }
    }
  
    // router bgp * / bgp enforce-first-as
    leaf enforce-first-as {
      description
        "Enforce the first AS for EBGP routes(default)";
      type empty;
    }

    //router bgp * /bgp enhanced-error
    leaf enhanced-error {
      description
        "Enabled BGP Enhanced error handling";
      type boolean;
    }
    
    // router bgp * / bgp fast-external-fallover
    leaf fast-external-fallover {
      description
        "Immediately reset session if a link to a directly connected external peer goes down";
      type boolean;
    }
    
    // router bgp * / bgp graceful-restart
    container graceful-restart {
      description
        "Graceful restart capability parameters";
      presence "Graceful restart capability parameters";
      leaf extended {
        type empty;
      }
      leaf restart-time {
        description
          "Set the max time needed to restart and come back up";
        type uint16 {
          range "1..3600";
        }
      }
      leaf stalepath-time {
        description
          "Set the max time to hold onto restarting peer's stale paths";
        type uint16 {
          range "1..3600";
        }
      }
    }

    // router bgp * / bgp ha-mode
    container ha-mode {
      description
        "Select BGP High Availability mode";
      container sso {
        description
          "BGP High Availability NSR sso mode";
        presence "true";
        leaf prefer {
          description
            "Prefer BGP High Availability NSR sso mode";
          type empty;
        }
      }
    }

    // router bgp * / bgp listen 
    container listen {
      description
        "Neighbor subnet range listener";
      leaf limit {
        description
          "Set the max limit for the dynamic subnet range neighbors";
        type uint16 {
          range "1..10000";
        }
      }
      list range {
        description
          "Subnet network range";
        key "network-range peer-group";
        leaf network-range {
          type union {
            type inet:ipv4-prefix;
            type ios-types:ipv6-prefix;
          }
        }
        leaf peer-group {
          description
            "Member of the peer-group";
          type string;
        }
      }
    }

    // router bgp * / bgp log-neighbor-changes
    leaf log-neighbor-changes {
      description
        "Log neighbor up/down and reset reason";
      default "true";
      type boolean;
    }
    
    // router bgp * / bgp maxas-limit
    leaf maxas-limit {
      description
        "Allow AS-PATH attribute from any neighbor imposing a limit on number of ASes";
      type uint16 {
        range "1..2000";
      }
    }

    // router bgp * / bgp maxcommunity-limit
    leaf maxcommunity-limit {
      description
        "Number of communities in the COMMUNITY attribute";
      type uint16 {
        range "1..1018";
      }
    }
  
    // router bgp * / bgp maxextcommunity-limit
    container maxextcommunity-limit {
      description
        "Allow EXTENDED COMMUNITY attribute from any neighbor imposing a
        limit on number of extended communities";
      leaf number {
        description 
          "Number of extended communities in the EXTENDED COMMUNITY
          attribute";
        type uint16 {
          range "1..509";
        }
      }
    }

    // router bgp * / bgp nopeerup-delay
    container nopeerup-delay {
      description
        "Set how long BGP will wait for the first peer to come up before beginning the update delay or graceful restart timers (in seconds)";
      leaf cold-boot {
        description
          "Delay in seconds";
        type uint16 {
          range "1..3600";
        }
      }
      leaf nsf-switchover {
        description
          "Delay in seconds";
        type uint16 {
          range "1..3600";
        }
      }
      leaf post-boot {
        description
          "Delay in seconds";
        type uint16 {
          range "1..3600";
        }
      }
      leaf user-initiated {
        description
          "Delay in seconds";
        type uint16 {
          range "1..3600";
        }
      }
    }

    // router bgp * / bgp refresh
    container refresh {
      description 
        "refresh";
      container max-eor-time {
        description 
          "Configure refresh max-eor time";
        leaf refresh-disable {
          type enumeration {
	    enum 0;
	  }
        }
        leaf timer-interval {
          type uint16 {
            range "600..3600";
          }
        }
      }
      container stalepath-time {
        description 
          "Configure refresh stale-path time";
        leaf refresh-disable {
          type enumeration {
	    enum 0;
	  }
        }
        leaf timer-interval {
          type uint16 {
            range "600..3600";
          }
        }
      }
    }

    // router bgp * / bgp regexp
    container regexp {
      description
        "Select regular expression engine";
      leaf deterministic {
        description
          "Enable bounded-execution-time regular expression engine";
        type boolean;
      }
    }

    // router bgp * / bgp route-map-cache
    leaf route-map-cache {
      description
        "Enable route-map caching";
      type empty;
    }

    uses bgp-router-id-grouping;

    // router bgp * / bgp sso
    container sso {
      description
        "Stateful Switchover";
      leaf route-refresh-enable {
        description
          "Enable SSO only for Route-Refresh capable peers";
        type empty;
      }
    }

    // router bgp * / transport
    container transport {
      description
        "Transport options";
      leaf path-mtu-discovery {
        description
          "Use transport path MTU discovery";
        type boolean;
      }
    }

    // router bgp * / bgp update-delay
    leaf update-delay {
      description
        "Set the max initial delay for sending update";
      type uint16 {
        range "1..3600";
      }
    }
  }

  // router bgp * / address-family * / bgp additional-paths
  grouping bgp-additional-paths-grouping {
    container additional-paths {
      description
        "Additional paths in the BGP table";
      leaf install {
        description
          "Additional paths to install into RIB";
        type empty;
      }
      leaf receive {
        description
          "Receive additional paths from neighbors";
        type empty;
      }
      container select {
        description
          "Selection criteria to pick the paths";
        container all {
          description
            "Select all available paths";
          presence "true";
          container best {
            description
              "Select best N paths";
            list range {
              key "range";
              leaf range {
                description
                  "Number of best paths in additional paths to be selected";
                type uint8 {
                  range "2..3";
                }
              }
              leaf group-best {
                description
                  "Select group-best path";
                type empty;
              }
            }
          }
          container group-best {
            description
              "Select group-best path";
            presence "true";
            leaf best {
              description
                "Number of best paths in additional paths to be selected";
              type uint8 {
                range "2..3";
              }
            }
          }
        }
        container backup {
          description
            "Select backup path";
          presence "true";
          leaf best-external {
            description
              "Select best-external path";
            type empty;
          }
        }
        container best {
          description
            "Select best N paths";
          list range {
            key "range";
            leaf range {
              description
                "Number of best paths in additional paths to be selected";
              type uint8 {
                range "2..3";
              }
            }
            leaf all {
              description
                "Select all available paths";
              type empty;
            }
            container group-best {
              description
                "Select group-best path";
              presence "true";
              leaf all {
                description
                  "Select all available paths";
                type empty;
              }
            }
          }
        }
        container best-external {
          description
            "Select best-external path";
          presence "true";
          leaf backup {
            description
              "Select backup path";
            type empty;
          }
        }
        container group-best {
          description
            "Select group-best path";
          presence "true";
          leaf all {
            description
              "Select all available paths";
            type empty;
          }
          leaf best {
            description
              "Number of best paths in additional paths to be selected";
            type uint8 {
              range "2..3";
            }
          }
        }
      }
      container send {
        description
          "Send additional paths to neighbors";
        presence "true";
        leaf receive {
          description
            "Receive additional paths from neighbors";
          type empty;
        }
      }
    }
  }

  // router bgp * / address-family * / bgp advertise-best-external
  grouping bgp-advertise-best-external-grouping {
    leaf advertise-best-external {
      description
        "Advertise best external path to internal peers";
      type empty;
    }
  }

  // router bgp * / address-family * / bgp aggregate-time
  grouping bgp-aggregate-timer-grouping {
    container aggregate-timer {
      description
        "Configure aggregation timer";
      choice timer-choice {
        leaf aggregate-timer {
          description
          "Timer interval";
          type uint8 {
            range "6..60";
          }
        }
        leaf disable-timer {
          description
          "Timer interval";
          type enumeration {
      enum 0;
          }
        }
      }
    }
  }

  // router bgp * / address-family * / bgp bestpath
  grouping bgp-bestpath-grouping {
    container bestpath {
      description
	"Change the default bestpath selection";
      container igp-metric {
	description
	  "igp metric";
	leaf ignore {
	  description
	    "Ignore igp metric in bestpath selection";
	  type empty;
	}
      }
      container prefix-validate {
	description
	  "Prefix origin validation";
	leaf allow-invalid {
	  description
	    "Allow invalid routes to be considered for bestpath";
	  type empty;
	}
	leaf disable {
	  description
	    "Disable prefix validation";
	  type empty;
	}
      }
    }
  }

  // router bgp * / address-family * / bgp dampening
  grouping bgp-dampening-grouping {
    container dampening {
      description
        "Enable route-flap dampening";
      presence "enable bgp route-flap dampening";
      choice dampening-choice {
        leaf route-map {
          description
            "Route-map to specify criteria for dampening";
          type string;
        }
        container dampen {
          leaf half-life-time {
            type uint8 {
              range "1 .. 45";
            }
          }
          leaf reuse-time {
            type uint16 {
              range "1 .. 20000";
            }
          }
          leaf suppress-time {
            type uint16 {
              range "1 .. 20000";
            }
          }
          leaf max-suppress-time {
            type uint8 {
              range "1 .. 255";
            }
          }
        }
      }
    }
  }

  // router bgp * / address-family * mvpn / bgp default
  grouping bgp-default-grouping {
    container default {
      description
        "Configure BGP defaults";
      leaf route-target {
        description
          "Control behavior based on Route-Target attributes";
        type enumeration {
          enum "filter";
        }
      }
    }
  }

  // router bgp * / address-family * / bgp dmzlink-bw
  grouping bgp-dmzlink-bw-grouping {
    leaf dmzlink-bw {
      description
        "Use DMZ Link Bandwidth as weight for BGP multipaths";
      type empty;
    }
  }

  // router bgp * / address-family * / bgp inject-map
  grouping bgp-inject-map-grouping {
    list inject-map {
      description
        "Route map which specifies prefixes to inject";
      key "name";
      leaf name {
        type string;
      }
      leaf exist-map {
        description
          "Route map which specifies exist condition";
        type string;
        //mandatory true;
      }
      leaf copy-attributes {
        description
          "Copy attributes from aggregate";
        type empty;
      }
    }
  }

  // router bgp * / address-family * / bgp nexthop
  grouping bgp-nexthop-grouping {
    container nexthop {
      description
        "Nexthop tracking commands";
      container trigger {
        description
          "Nexthop triggering";
        leaf delay {
          description
            "Set the delay to trigger nexthop tracking";
          type uint8 {
            range "0..100";
          }
        }
        leaf enable {
          description
            "Enable nexthop tracking";
          type boolean;
        }
      }
      leaf route-map {
        description
          "Route map for valid nexthops";
        type string;
      }
    }
  }

  // router bgp * / address-family * / bgp recursion
  grouping bgp-recursion-grouping {
    container recursion {
      description
        "recursion rule for the nexthops";
      leaf host {
        description
          "recursion via host for the nexthops";
        type empty;
      }
    }
  }

  // router bgp * / address-family * / bgp redistribute-internal
  grouping bgp-redistribute-internal-grouping {
    leaf redistribute-internal {
      description
        "Allow redistribution of iBGP into IGPs (dangerous)";
      type empty;
    }
  }

  // router bgp * / address-family * / bgp route-map
  grouping bgp-route-map-grouping {
    container route-map {
      description
        "bgp route-map commands";
      leaf priority {
        description
          "Have route-map set commands take priority over BGP commands such as
	  next-hop-unchanged";
        type empty;
      }
    }
  }

  // router bgp * / address-family * / bgp scan-time
  grouping bgp-scan-time-grouping {
    leaf scan-time {
      description
        "Configure background scanner interval";
      type uint8 {
        range "5..60";
      }
    }
  }

  // router bgp * / address-family * / bgp slow-peer
  grouping bgp-slow-peer-grouping {
    container slow-peer {
      description
        "Configure slow-peer";
      container detection {
        description
          "Slow-peer detection";
        presence "true";
        leaf disable {
          description
            "Disable slow-peer detection";
          type empty;
        }
        leaf threshold {
          description
            "Threshold value (seconds)";
          type uint16 {
            range "120..3600";
          }
        }
      }
      container split-update-group {
        description
          "Configure slow-peer split-update-group";
        container dynamic {
          description
            "Dynamically split the slow peer to slow-update group";
          presence "true";
          leaf permanent {
            description
              "Keep the slow-peer permanently in slow-update group";
            type empty;
          }
        }
      }
    }
  }

  // router bgp * / address-family * / bgp soft-reconfig-backup
  grouping bgp-soft-reconfig-backup-grouping {
    leaf soft-reconfig-backup {
      description
        "Use soft-reconfiguration inbound only when route-refresh is not negotiated";
      type empty;
    }
  }

  // router bgp * / address-family * / bgp suppress-inactive
  grouping bgp-suppress-inactive-grouping {
    leaf suppress-inactive {
      description
        "Suppress routes that are not in the routing table";
      type empty;
    }
  }

  // router bgp * / address-family * / bgp update-group
  grouping bgp-update-group-grouping {
    container update-group {
      description
        "Manage peers in bgp update groups";
      container split {
        description
          "Split update groups based on Policy";
        leaf as-override {
          description
            "Keep peers with as-override in different update groups";
          type empty;
        }
      }
    }
  }

  // router bgp * / address-family ipv4 unicast / neighbor * activate
  grouping ipv4-unicast-neighbor-activate-grouping {
    leaf activate {
      description
        "Enable the address family for this neighbor";
            //must "(../remote-as or ../peer-group)" {
            // }
      type boolean;
    }
  }

  // router bgp * / address-family * / neighbor * activate
  grouping neighbor-activate-grouping {
    leaf activate {
      description
        "Enable the address family for this neighbor";
            //must "(../remote-as or ../peer-group)" {
            // }
      type empty;
    }
  }

  // router bgp * / address-family * / additional-paths
  grouping neighbor-additional-paths-grouping {
    container additional-paths {
      leaf disable {
        description
          "Disable additional paths for this neighbor";
        type empty;
      }
      leaf receive {
        description
          "Receive additional paths from neighbors";
        type empty;
      }
      container send {
        description
          "Send additional paths to this neighbor";
        presence "true";
        leaf receive {
          description
            "Receive additional paths from this neighbor";
          type empty;
        }
      }
    }
  }

  // router bgp * / address-family * / neighbor * advertise
  grouping neighbor-advertise-grouping {
    container advertise {
      description
        "Advertise to this neighbor";
      container additional-paths {
        description
          "Advertise additional paths";
        container all {
          description
            "Select all available paths";
          presence "true";
          container best {
            description
              "Select best N paths";
            list best-range {
              key "range";
              leaf range {
                description
                  "Number of best paths in additional paths to be selected";
                type uint8 {
                  range "2..3";
                }
              }
              leaf group-best {
                description
                  "Select group-best paths";
                type empty;
              }
            }
          }
          container group-best {
            description
              "Select group-best paths";
            presence "true";
            leaf best {
              description
                "Number of best paths in additional paths to be selected";
              type uint8 {
                range "2..3";
              }
            }
          }
        }
        container best {
          description
            "Select best N paths";
          list best-range {
            key "range";
            leaf range {
              description
                "Number of best paths in additional paths to be selected";
              type uint8 {
                range "2..3";
              }
            }
            leaf all {
              description
                "Select all available paths";
              type empty;
            }
            container group-best {
              description
                "Select group-best paths";
              presence "true";
              leaf all {
                description
                  "Select all available paths";
                type empty;
              }
            }
          }
        }
        container group-best {
          description
            "Select group-best paths";
          presence "true";
          leaf all {
            description
              "Select all available paths";
            type empty;
          }
          leaf best {
            description
              "Number of best paths in additional paths to be selected";
            type uint8 {
              range "2..3";
            }
          }
        }
      }
      leaf best-external {
        description
          "Advertise best-external (at RRs best-internal) path";
        type empty;
      }
      container diverse-path {
        description
          "Advertise diverse path";
        container backup {
          description
            "Diverse path can be backup path";
          presence "true";
          leaf mpath {
            description
              "Diverse path can be multipath";
            type empty;
          }
        }
        leaf mpath {
          description
            "Diverse path can be multipath";
          type empty;
        }
      }
    }
  }

  // router bgp * / address-family * / neighbor * advertise-map
  grouping neighbor-advertise-map-grouping {
    container advertise-map {
      description
        "specify route-map for conditional advertisement";
      list name {
        key "word";
        leaf word {
          description
            "advertise route-map name";
          type string;
        }
        leaf exist-map {
          description
            "condition route-map name";
          type string;
        }
        leaf non-exist-map {
          description
            "condition route-map name";
          type string;
        }
      }
    }
  }

  // router bgp * / address-family * / neighbor * advertisement-interval
  grouping neighbor-advertisement-interval-grouping {
    leaf advertisement-interval {
      description
        "Minimum interval between sending BGP routing updates";
      type uint16 {
        range "0..600";
      }
    }
  }

  // router bgp * / address-family * / neighbor * aigp
  grouping neighbor-aigp-grouping {
    container aigp {
      description
        "Enable a AIGP on neighbor";
      presence "true";
      container send {
        description
          "Cost community or MED carrying AIGP VALUE";
        container cost-community {
          description
            "Cost extended community carrying AIGP Value";
          list cc-range {
            key "range";
            leaf range {
              description
                "Community ID";
              type uint8 {
                range "0..255";
              }
            }
            container poi {
              description
                "Point of insertion";
              container igp-cost {
                description
                  "Point of insertion after IGP";
                presence "true";
                leaf transitive {
                  description
                    "Cost community is transitive";
                  type empty;
                }
              }
              container pre-bestpath {
                description
                  "Point of insertion at beginning";
                presence "true";
                leaf transitive {
                  description
                    "Cost community is transitive";
                  type empty;
                }
              }
            }
          }
        }
        leaf med {
          description
            "Med carrying AIGP Value";
          type empty;
        }
      }
    }
  }

  // router bgp * / address-family * / neighbor * allow-policy
  grouping neighbor-allow-policy-grouping {
    leaf allow-policy {
      description
        "Enable the policy support for this IBGP Neighbor";
      type empty;
    }
  }

  // router bgp * / address-family * / neighbor * allowas-in
  grouping neighbor-allowas-in-grouping {
    container allowas-in {
      description
        "Accept as-path with my AS present in it";
      presence "accept as-paths";
      leaf as-number {
        type uint8 {
          range "1..10";
        }
      }
    }
  }

  // router bgp * / address-family * / neighbor * announce
  grouping neighbor-announce-grouping {
    container announce {
      description
        "Announce RPKI state using an extended community";
      container rpki {
        description
          "Announce RPKI information using an extended community";
        leaf state {
          description
            "Announce RPKI state information using an extended community";
          type empty;
        }
      }
    }
  }

  // router bgp * / address-family * / neighbor * as-override
  grouping neighbor-as-override-grouping {
    container as-override {
      description
        "Override matching AS-number while sending update";
      presence "true";
      leaf disable {
        type empty;
      }
    }
  }

  // router bgp * / address-family * / neighbor * capability
  grouping neighbor-capability-grouping {
    container capability {
      description
        "Advertise capability to the peer";
      container orf {
        description
          "Advertise ORF capability to the peer";
        leaf-list prefix-list {
          description
            "Advertise prefix list ORF capability to this neighbor";
          max-elements "1";
          type enumeration {
            enum "both";
            enum "receive";
            enum "send";
          }
        }
      }
    }
  }

  // router bgp * / address-family * / neighbor * default-originate
  grouping neighbor-default-originate-grouping {
    container default-originate {
      description
        "Originate default route to this neighbor";
      presence "enable originate default route to this neighbor";
      leaf route-map {
        description
          "Route-map to specify criteria to originate default";
        type string;
      }
    }
  }

  // router bgp * / address-family * / neighbor * distribute-list
  grouping neighbor-distribute-list-grouping {
    list distribute-list {
      description
        "Filter updates to/from this neighbor";
      key "inout";
      leaf inout {
        type enumeration {
          enum "in" {
          }
          enum "out" {
          }
        }
      }
      leaf accesslist {
        type ios-types:bgp-distribute-list-type2;
        mandatory true;
      }
    }
  }

  // router bgp * / address-family * / neighbor * dmzlink-bw
  grouping neighbor-dmzlink-bw-grouping {
    leaf dmzlink-bw {
      description
        "Propagate the DMZ link bandwidth";
      type empty;
    }
  }

  // router bgp * / address-family * / neighbor * encap
  grouping neighbor-encap-grouping {
    container encap {
      description 
        "Preferred encapsulation for neighbor";      
      choice encap-choice {
        leaf mpls {
          description 
            "Neighbor prefers MPLS";      
          type empty;
        }
        leaf vxlan {
          description
            "Neighbor prefers VxLAN";      
          type empty;
        }
      }
    }
  }

  // router bgp * / address-family * / neighbor * filter-list
  grouping neighbor-filter-list-grouping {
    list filter-list {
      description
        "Establish BGP filters";
      key "inout";
      leaf inout {
        type enumeration {
          enum "in" {
          }
          enum "out" {
          }
        }
      }
      leaf as-path-list {
        type uint16 {
          range "1..500";
        }
        mandatory true;
      }
    }
  }

  // router bgp * / address-family * / neighbor * maximum-prefix
  grouping neighbor-maximum-prefix-grouping {
    container maximum-prefix {
      description
        "Maximum number of prefixes accepted from this peer";
      leaf max-prefix-no {
        type uint32 {
          range "1..2147483647";
        }
      }
      leaf threshold {
        type uint8 {
          range "1..100";
        }
      }
      leaf restart {
        description
          "Restart bgp connection after limit is exceeded";
        type uint16 {
          range "1..65535";
        }
      }
      leaf warning-only {
        description
          "Only give warning message when limit is exceeded";
        type empty;
      }
    }
  }

  // router bgp * / address-family * / neighbor * next-hop-self
  grouping neighbor-next-hop-self-grouping {
    container next-hop-self {
      description
        "Disable the next hop calculation for this neighbor";
      presence "true";
      leaf all {
        description
          "Enable next-hop-self for both eBGP and iBGP received paths";
        type empty;
      }
    }
  }

  // router bgp * / address-family * / neighbor * next-hop-unchanged
  grouping neighbor-next-hop-unchanged-grouping {
    leaf next-hop-unchanged {
      description
        "Propagate the iBGP paths' next hop unchanged for this neighbor";
      type empty;
    }
  }

  // router bgp * / address-family * / neighbor * peer-group
  grouping neighbor-peer-group-grouping {
    container peer-group {
      description
        "Member of the peer-group";
      presence "true";
      leaf peer-group-name {
        description
          "peer-group name";
        type string;
      }
    }
  }

  // router bgp * / address-family * / neighbor * peer-group
  grouping peer-group-peer-group-grouping {
    leaf peer-group {
      description
        "Member of the peer-group";
      type empty;
      mandatory true;
    }
  }

  // router bgp * / address-family * / neighbor * prefix-list
  grouping neighbor-prefix-list-grouping {
    list prefix-list {
      description
        "Filter updates to/from this neighbor";
      key "inout";
      leaf inout {
        type enumeration {
          enum "in" {
          }
          enum "out" {
          }
        }
      }
      leaf prefix-list-name {
        type string;
        mandatory true;
      }
    }
  }

  // router bgp * / address-family * / neighbor * remove-private-as
  grouping neighbor-remove-private-as-grouping {
    container remove-private-as {
      description
        "Remove private AS number from outbound updates";
      presence true;
      container all {
        description
          "Remove all private AS numbers";
        presence true;
        leaf replace-as {
          description
            "Replace all private AS numbers with local AS";
          type empty;
        }
      }
    }
  }

  // router bgp * / address-family * / neighbor * route-map
  grouping neighbor-route-map-grouping {
    list route-map {
      description
        "Apply route map to neighbor";
      key "inout";
      leaf inout {
        type enumeration {
          enum "in" {
          }
          enum "out" {
          }
        }
      }
      leaf route-map-name {
        type string;
        mandatory true;
      }
    }
  }

  // router bgp * / address-family * / neighbor * route-reflector-client
  grouping neighbor-route-reflector-client-grouping {
    leaf route-reflector-client {
      description
        "Configure a neighbor as Route Reflector client";
      type empty;
    }
  }

  // router bgp * / address-family * / neighbor * send-community
  grouping neighbor-send-community-grouping {
    container send-community {
      description
        "Send Community attribute to this neighbor";
      presence "true";
      leaf send-community-where {
        default "standard";
        type enumeration {
          enum "both";
          enum "extended";
          enum "standard" {
          }
        }
      }
    }
  }

  // router bgp * / address-family * / neighbor * send-label
  grouping neighbor-send-label-grouping {
    container send-label {
      description
        "Send NLRI + MPLS Label to this peer";
      presence "true";
      leaf send-label-explicit {
        type enumeration {
          enum "explicit-null" {
          }
        }
      }
    }
  }

  // router bgp * / address-family * / neighbor * slow-peer
  grouping neighbor-slow-peer-grouping {
   container slow-peer {
      description
        "Configure slow-peer";
      container detection {
        description
          "Slow-peer detection";
        presence "true";
        leaf threshold {
          description
            "Threshold value (seconds)";
          type uint16 {
            range "120..3600";
          }
        }
      }
      container split-update-group {
        description
          "Configure slow-peer split-update-group";
        container dynamic {
          description
            "Dynamically split the slow peer to slow-update group";
          presence "true";
          leaf permanent {
            description
              "Keep the slow-peer permanently in slow-update group";
            type empty;
          }
        }
      }
    }
  }

  // router bgp * / address-family * / neighbor * soft-reconfiguration
  grouping neighbor-soft-reconfiguration-grouping {
    leaf soft-reconfiguration {
      description
        "Per neighbor soft reconfiguration";
      type enumeration {
        enum "inbound";
      }
    }
  }

  // router bgp * / address-family * / neighbor * soo
  grouping neighbor-soo-grouping {
    leaf soo {
      description
        "ASN:nn or IP-address:nn VPN extended community";
      type string;
    }
  }

  // router bgp * / address-family * / neighbor * translate-update
  grouping neighbor-translate-update-grouping {
    container translate-update {
      description
        "Translate update to MBGP format";
      container ipv4 {
        description
          "Address Family";
        container multicast {
          description
            "Address Family modifier";
          presence "Address Family modifier";
          leaf unicast {
            description
              "Address Family modifier";
            type empty;
          }
        }
      }
    }
  }

  // router bgp * / address-family * / neighbor * unsuppress-map
  grouping neighbor-unsuppress-map-grouping {
    leaf unsuppress-map {
      description
        "Route-map to selectively unsuppress suppressed routes";
      type string;
    }
  }

  // router bgp * / address-family * / neighbor * weight
  grouping neighbor-weight-grouping {
    leaf weight {
      description
        "Set default weight for routes from this neighbor";
      type uint16 {
        range "0..65535";
      }
    }
  }

  // router bgp * / address-family * / neighbor * cluster-id
  grouping neighbor-cluster-id-grouping {
    leaf cluster-id {
      type union {
        type uint32 {
          range "1..4294967295";
        }
        type inet:ipv4-address;
      }
    }
  }

  // router bgp * / address-family * / neighbor * description
  grouping neighbor-description-grouping {
    leaf description {
      description
        "Neighbor specific description";
      type string;
    }
  }

  // router bgp * / address-family * / neighbor * disable-connected-check
  grouping neighbor-disable-connected-check-grouping {
    leaf disable-connected-check {
      description 
        "one-hop away EBGP peer using loopback address";
      type empty;
    }
  }

  // router bgp * / address-family * / neighbor * ebgp-multihop
  grouping neighbor-ebgp-multihop-grouping {
    container ebgp-multihop {
      description
        "Allow EBGP neighbors not on directly connected networks";
      presence "Allow EBGP neighbors not on directly connected networks";
      leaf max-hop {
        type uint8 {
          range "1..255";
        }
      }
    }
  }

  // router bgp * / address-family * / neighbor * fall-over
  grouping neighbor-fall-over-grouping {
    container fall-over {
      description
        "session fall on peer route lost";
      presence "true";
      container bfd {
        description
          "Use BFD to detect failure";
        presence "true";
        choice hop-choice {
          leaf multi-hop {
            description
              "Force BFD multi-hop to detect failure";
            type empty;
          }
          leaf single-hop {
            description
              "Force BFD single-hop to detect failure";
            type empty;
          }
        }
        leaf check-control-plane-failure {
          description
            "Retrieve control plane dependent failure info from BFD for BGP
            GR/NSR operation";
                type empty;
        }
        leaf strict-mode {
          description
            "Enable BFD strict-mode";
                type empty;
        }
      }
      leaf route-map-name {
        type string;
      }
    }
  }

  // router bgp * / address-family * / neighbor * ha-mode
  grouping neighbor-ha-mode-grouping {
    container ha-mode {
      description
        "high availability mode";
      container graceful-restart {
        description
          "graceful-restart for this peer";
        presence "true";
        leaf disable {
          description
            "disable graceful-restart";
          type empty;
        }
      }
      container sso {
        description
          "stateful-switchover support for this peer";
        presence "true";
        leaf disable {
          description
            "disable stateful-switchover";
          type empty;
        }
      }
    }
  }

  // router bgp * / address-family * / neighbor * inherit
  grouping neighbor-inherit-grouping {
    container inherit {
      description
        "Inherit a template";
      leaf peer-policy {
        description
          "Inherit a peer-policy template";
        type string;
      }
      leaf peer-session {
        description
          "Inherit a peer-session template";
        type string;
      }
    }
  }

  // router bgp * / address-family * / neighbor * local-as
  grouping neighbor-local-as-grouping {
    container local-as {
      description
        "Specify a local-as number";
      presence "Specify a local-as number";
      leaf as-no {
        type ios-types:bgp-as-number-type;
      }
      leaf no-prepend {
        description
          "Do not prepend local-as to updates from ebgp peers";
        type empty;
      }
      leaf replace-as {
        description
          "Replace real AS with local AS in the EBGP updates";
        type empty;
      }
      leaf dual-as {
        description
          "Accept either real AS or local AS from the ebgp peer";
        type empty;
      }
    }
  }

  // router bgp * / address-family * / neighbor * log-neighbor-changes
  grouping neighbor-log-neighbor-changes-grouping {
    container log-neighbor-changes {
      description
        "Log neighbor up/down and reset reason";
      presence "true";
      leaf disable {
        description
          "disable";
        type empty;
      }
    }
  }

  // router bgp * / address-family * / neighbor * password
  grouping neighbor-password-grouping {
    container password {
      description
        "Set a password";
      leaf enctype {
        type uint8 {
          range "0..7";
        }
      }
      leaf text {
        type string;
      }
    }
  }

  // router bgp * / address-family * / neighbor * path-attribute
  grouping neighbor-path-attribute-grouping {
    container path-attribute {
      description
        "BGP optional attribute filtering";
      container discard {
        description
          "Discard matching path-attribute for this neighbor";
        uses bgp-path-range-grouping;
      }
      container treat-as-withdraw {
        description
          "Treat-as-withdraw matching path-attribute for this neighbor";
        uses bgp-path-range-grouping;
      }
    }
  }

  // neighbor path-attribute grouping
  grouping bgp-path-range-grouping {
    container attibute_type {
      leaf type {
        description
          "path attribute type";
        type uint8 {
          range "1..255";
        }
      }
      leaf in {
        description
          "Perform inbound path-attribute filtering";
        type empty;
      }
    }
    container range {
      leaf start_value {
        description
          "path attribute range start value";
        type uint8 {
          range "1..255";
        }
      }
      leaf end_value {
        description
          "path attribute range end value";
        type uint8 {
          range "1..255";
        }
      }
      leaf in {
        description
          "Perform inbound path-attribute filtering";
        type empty;
      }
    }
  }

  // router bgp * / address-family * / neighbor * remote-as
  grouping neighbor-remote-as-grouping {
    leaf remote-as {
      description
        "Specify a BGP neighbor";
      type union {
        type uint32 {
          range "1..4294967295";
        }
        type string;
      }
      mandatory true;
    }
  }

  // router bgp * / address-family * / neighbor * remote-as
  grouping peer-group-remote-as-grouping {
    leaf remote-as {
      description
        "Specify a BGP peer-group remote-as";
      type union {
        type uint32 {
          range "1..4294967295";
        }
        type string;
      }
    }
  }

  // router bgp * / address-family * / neighbor * shutdown
  grouping neighbor-shutdown-grouping {
    leaf shutdown {
      description
        "Administratively shut down this neighbor";
      type empty;
    }
  }

  // router bgp * / address-family * / neighbor * timers
  grouping neighbor-timers-grouping {
    container timers {
      description
        "BGP per neighbor timers";
      leaf keepalive-interval {
        type uint16 {
          range "0..65535";
        }
      }
      leaf holdtime {
        type uint16 {
          range "0..65535";
        }
      }
      leaf minimum-neighbor-hold {
        type uint16 {
          range "0..65535";
        }
      }
    }
  }

  // router bgp * / address-family * / neighbor * transport
  grouping neighbor-transport-grouping {
    container transport {
      description
        "Transport options";
      leaf connection-mode {
        description
          "Specify passive or active connection";
        type enumeration {
          enum "active" {
          }
          enum "passive" {
          }
        }
      }
      leaf multi-session {
        description
          "Use multi-session for transport";
        type empty;
      }
      container path-mtu-discovery {
        description
          "Use transport path MTU discovery";
        presence "true";
        leaf disable {
          description
            "disable";
          type empty;
        }
      }
    }
  }

  // router bgp * / address-family * / neighbor * ttl-security
  grouping neighbor-ttl-security-grouping {
    container ttl-security {
      description
        "BGP ttl security check";
      leaf hops {
        description
          "IP hops";
        type uint8 {
          range "1..254";
        }
      }
    }
  }

  // router bgp * / address-family * / neighbor * update-source
  grouping neighbor-update-source-grouping {
    container update-source {
      description
        "Source of routing updates";
      uses ios-ifc:interface-grouping;
    }
  }

  // router bgp * / address-family * / neighbor * version
  grouping neighbor-version-grouping { 
    leaf version {
      description
        "Set the BGP version to match a neighbor";
      type uint16 {
        range "4";
      }
    }
  }

  // router bgp * / address-family * / advertise
  grouping address-family-advertise-grouping {
    container advertise {
      description
        "Configure path advertise/export to other address-family";
      container l2vpn {
        description
          "Address family for VRF advertise/export"; 
        leaf evpn {
          description
            "Advertise/export prefixes to l2vpn evpn table";      
          type empty;
        }
      }
    }
  }

  // router bgp * / address-family ipv4 * / aggregate-address
  grouping address-family-ipv4-aggregate-address-grouping {
    list aggregate-address {
      description
        "Configure BGP aggregate entries";
      key "ipv4-address ipv4-mask";
      leaf ipv4-address {
        type inet:ipv4-address;
      }
      leaf ipv4-mask {
        type inet:ipv4-address;
      }
      leaf advertise-map {
        description
          "Set condition to advertise attribute";
        type string;
      }
      leaf as-set {
        description
          "Generate AS set path information";
        type empty;
      }
      leaf attribute-map {
        type string;
      }
      leaf as-override {
        description
          "Override matching AS-number while sending update";
        type empty;
      }
      leaf route-map {
        type string;
      }
      leaf summary-only {
        description
          "Filter more specific routes from updates";
        type empty;
      }
      leaf suppress-map {
        description
          "Conditionally filter more specific routes from updates";
        type string;
      }
    }
  }

  // router bgp * / address-family ipv6 * / aggregate-address
  grouping address-family-ipv6-aggregate-address-grouping {
    list aggregate-address {
      description
        "Configure BGP aggregate entries";
      key "ipv6-address";
      leaf ipv6-address {
        type ios-types:ipv6-prefix;
      }
      leaf advertise-map {
        description
          "Set condition to advertise attribute";
        type string;
      }
      leaf as-set {
        description
          "Generate AS set path information";
        type empty;
      }
      leaf attribute-map {
        type string;
      }
      leaf as-override {
        description
          "Override matching AS-number while sending update";
        type empty;
      }
      leaf route-map {
        type string;
      }
      leaf summary-only {
        description
          "Filter more specific routes from updates";
        type empty;
      }
      leaf suppress-map {
        description
          "Conditionally filter more specific routes from updates";
        type string;
      }
    }
  }

  // router bgp * / address-family * / auto-summary
  grouping address-family-auto-summary-grouping {
    leaf auto-summary {
      description
        "Enable automatic network number summarization";
      type empty;
    }
  }

  // router bgp * / address-family * / default-information
  grouping address-family-default-information-grouping {
    container default-information {
      description
        "Control distribution of default information";
      leaf originate {
        description
          "Distribute a default route";
        type empty;
      }
    }
  }

  // router bgp * / address-family * / default-metric
  grouping address-family-default-metric-grouping {
    leaf default-metric {
      description
        "Set metric of redistributed routes";
      type uint32 {
        range "1..4294967295";
      }
    }
  }

  // router bgp * / address-family * / distance
  grouping address-family-distance-grouping {
    container distance {
      description
        "Define an administrative distance";
      container bgp {
        description
          "BGP distance";
        leaf extern-as {
          type uint16 {
            range "1..255";
          }
        }
        leaf internal-as {
          type uint16 {
            range "1..255";
          }
        }
        leaf local {
          type uint16 {
            range "1..255";
          }
        }
      }
      list adm-distance {
        key "distance srcip wildbits";
        leaf distance {
          type uint16 {
            range "1..255";
          }
        }
        leaf srcip {
          type inet:ipv4-address;
        }
        leaf wildbits {
          type inet:ipv4-address;
        }
        leaf acl {
          type union {
            type uint16 {
              range "1..99";
            }
            type uint16 {
              range "1300..1999";
            }
            type string {
              pattern "[a-zA-Z].*";
            }
          }
        }
      }
    }
  }

  // router bgp * / address-family * / distribute-list
  grouping address-family-distribute-list-grouping {
    list distribute-list {
      description
        "Filter networks in routing updates";
      key "id";
      leaf id {
        type ios-types:bgp-distribute-list-type;
      }
      choice in-out-choice {
        container in {
          presence "enable incoming routing updates";
          description
            "Filter incoming routing updates";
          leaf interface {
            type string;
          }
        }
        container out {
          presence "enable outgoing routing updates";
          description
            "Filter outgoing routing updates";
          leaf interface {
            type string;
          }
        }
      }
    }
  }

  // router bgp * / address-family l2vpn * / import
  grouping address-family-l2vpn-import-grouping {
    container import {
      description "Configure path import";
      container vpnv4 {
        leaf unicast {
          type empty;
	  //mandatory true;
        }
        leaf re-originate {
          type empty;
        }
      }
      container vpnv6 {
        leaf unicast {
          type empty;
	  //mandatory true;
        }
        leaf re-originate {
          description
            "Imported path with RT re-originate";      
          type empty;
        }
      }
    }
  }

  // router bgp * / address-family vpnv4 * / import
  grouping address-family-vpnv4-import-grouping {
    container import {
      description "Configure path import";
      container l2vpn {
        description 
          "Configure EVPN to VPN path import";
        leaf evpn {
          type empty;
        }
        leaf re-originate {
          type empty;
        }
      }
    }
  }

  // router bgp * / address-family vpnv6 * / import
  grouping address-family-vpnv6-import-grouping {
    container import {
      description "Configure path import";
      container l2vpn {
        description 
          "Configure EVPN to VPN path import";
        leaf evpn {
          type empty;
        }
        leaf re-originate {
          type empty;
        }
      }
    }
  }

  // router bgp * / address-family vrf * / import
  grouping address-family-vrf-import-grouping {
    container import {
      description "Configure path import";
      container path {
        description "Path selection and path limit";
        leaf limit {
          description "Per net imported path limit";
          type uint8 {
            range "2..255";
          }
        }
        container selection {
          description
            "Path selection policy";
          leaf all {
            description
              "Import all available paths";
            type empty;
          }
        }
      }
      container vpnv4 {
        leaf unicast {
          type empty;
        }
        leaf re-originate {
          type empty;
        }
      }
      container vpnv6 {
        leaf unicast {
          type empty;
        }
        leaf re-originate {
          description
            "Imported path with RT re-originate";      
          type empty;
        }
      }
      container l2vpn {
        description 
          "Configure EVPN to VPN path import";
        leaf evpn {
          type empty;
        }
        leaf re-originate {
          type empty;
        }
      }
    }
  }

  // router bgp * / address-family * / maximum-paths
  grouping address-family-maximum-paths-grouping {
    container maximum-paths {
      description
        "Forward packets over multiple paths";
      choice max-path-choice {
        leaf ebgp {
          type uint16 {
            range "1..32";
          }
        }
        leaf eibgp {
          description
            "Both eBGP and iBGP paths as multipath";
          type uint16 {
            range "1..32";
          }
        }
        container ibgp {
          description
            "iBGP-multipath";
          choice ibgp-choice {
            leaf unequal-cost {
              description
                "Perform un-equal cost multipath selection";
              type uint16 {
                range "1..32";
              }
            }
            leaf max {
              type uint16 {
                range "1..32";
              }
            }
          }
        }
      }
      container external-rtfilter {
        description
          "VPN prefix multipath on external RT-Filter peers";
        leaf max {
          type uint16 {
            range "1..32";
          }
        }
      }
    }
  }

  // router bgp * / address-family ipv4 * / network
  grouping address-family-ipv4-network-grouping {
    container network {
      list with-mask {
        description
          "Specify a network to announce via BGP";
        key "number mask";
        leaf number {
          type inet:ipv4-address;
        }
        leaf mask {
          description
            "Network mask";
          type inet:ipv4-address;
        }
        leaf route-map {
          description
            "Route-map to modify the attributes";
          type string;
        }
        leaf backdoor {
          description
            "Specify a BGP backdoor route";
          type empty;
        }
      }
      list no-mask {
        description
          "Specify a network to announce via BGP";
        key "number";
        leaf number {
          type inet:ipv4-address;
        }
        leaf route-map {
          description
            "Route-map to modify the attributes";
          type string;
        }
        leaf backdoor {
          description
            "Specify a BGP backdoor route";
          type empty;
        }
      }
    }
  }

  // router bgp * / address-family ipv4 vrf * / network
  grouping address-family-vrf-ipv4-network-grouping {
    container network {
      list with-mask {
        description
          "Specify a network to announce via BGP";
        key "number mask";
        leaf number {
          type inet:ipv4-address;
        }
        leaf mask {
          description
            "Network mask";
          type inet:ipv4-address;
        }
        leaf route-map {
          description
            "Route-map to modify the attributes";
          type string;
        }
        leaf backdoor {
          description
            "Specify a BGP backdoor route";
          type empty;
        }
	leaf evpn {
	  description
	    "Advertise or export to EVPN address-family";
	  type empty;  
	}
      }
      list no-mask {
        description
          "Specify a network to announce via BGP";
        key "number";
        leaf number {
          type inet:ipv4-address;
        }
        leaf route-map {
          description
            "Route-map to modify the attributes";
          type string;
        }
        leaf backdoor {
          description
            "Specify a BGP backdoor route";
          type empty;
        }
	leaf evpn {
	  description
	    "Advertise or export to EVPN address-family";
	  type empty;  
	}
      }
    }
  }
  
  // router bgp * / address-family nsap * / network
  grouping address-family-nsap-network-grouping {
    list network {
      description
        "Specify a network to announce via BGP";
      key "number";
      leaf number {
        type inet:ipv4-address;
      }
      leaf route-map {
        description
          "Route-map to modify the attributes";
        type string;
      }
    }
  }

  // router bgp * / address-family ipv6 * / network
  grouping address-family-ipv6-network-grouping {
    list network {
      description
        "Specify a network to announce via BGP";
      key "number";
      leaf number {
        type ios-types:ipv6-prefix;
      }
      leaf route-map {
        description
          "Route-map to modify the attributes";
        type string;
      }
      leaf backdoor {
        description
          "Specify a BGP backdoor route";
        type empty;
      }
    }
  }

  // router bgp * / address-family ipv6 vrf * / network
  grouping address-family-vrf-ipv6-network-grouping {
    list network {
      description
        "Specify a network to announce via BGP";
      key "number";
      leaf number {
        type ios-types:ipv6-prefix;
      }
      leaf route-map {
        description
          "Route-map to modify the attributes";
        type string;
      }
      leaf backdoor {
        description
          "Specify a BGP backdoor route";
        type empty;
      }
      leaf evpn {
	description
	  "Advertise or export to EVPN address-family";
	type empty;  
      }
    }
  }

  // router bgp * / address-family * / redistribute
  grouping address-family-redistribute-grouping {
    container redistribute {
      description
        "Redistribute information from another routing protocol";
      container application {
        description
          "Application";
        presence "true";
        list name {
          key "name";
          leaf name {
            description
              "WORD :: Route-map name";
            type string;
          }
          uses metric-route-map-grouping;
        }
      }
      container bgp {
        description
          "Border Gateway Protocol (BGP)";
        leaf as-no {
          type ios-types:bgp-as-number-type;
        }
        uses metric-route-map-grouping;
      }
      container connected {
        description
          "Connected";
        presence "Connected";
        uses metric-route-map-grouping;
      }
      container dvmrp {
        description
          "Redistribution of DVMRP into BGP IPv4 Multicast";
        presence "Redistribution of DVMRP into BGP IPv4 Multicast";
        uses route-map-metric-grouping;
      }
      container eigrp {
        description
          "Enhanced Interior Gateway Routing Protocol (EIGRP)";
        leaf as-no {
          type uint16 {
            range "1..65535";
          }
        }
        uses metric-route-map-grouping;
      }
      container isis {
        description
          "ISO IS-IS";
        presence "true";
        list isis-area {
          key "name";
          leaf name {
            type string;
          }
          uses redistribute-isis-grouping;
        }
        container default {
          uses redistribute-isis-grouping;
        }
      }
      container lisp {
        description
          "Locator/ID Separation Protocol";
        presence "lisp";
        leaf include-connected {
          type empty;
        }
        uses metric-route-map-grouping;
      }
      container iso-igrp {
        description
          "IGRP for OSI networks";
        list iso-igrp-area {
          key "name";
          leaf name {
            type string;
          }
          uses route-map-metric-grouping;
        }
        container default {
          uses route-map-metric-grouping;
        }
      }
      container mobile {
        presence "Mobile routes";
        description
          "Mobile routes";
        uses metric-route-map-grouping;
      }
      container odr {
        presence "On Demand stub Routes";
        description
          "On Demand stub Routes";
        uses metric-route-map-grouping;
      }
      list ospf {
        description
          "Open Shortest Path First (OSPF)";
        key "id";
        leaf id {
          type uint16 {
            range "1..65535";
          }
        }
        list vrf {
          description
            "VPN Routing/Forwarding Instance";
          key "name";
          leaf name {
            type string;
          }
          container match;
          uses metric-route-map-grouping;
        }
        container non-vrf {
          uses redistribute-ospf-non-vrf-grouping;
        }
      }
      list ospfv3 {
        description
          "OSPFv3";
        key "id";
        leaf id {
          type uint16 {
            range "1..65535";
          }
        }
        uses redistribute-ospf-non-vrf-grouping;
      }
      container rip {
        presence "Routing Information Protocol (RIP)";
        description
          "Routing Information Protocol (RIP)";
        uses metric-route-map-grouping;
        leaf name {
          description "User selected string identifying this process";
          type string;
        }
      }
      container static {
        presence "Static routes";
        description
          "Static routes";
        container clns {
          description
            "Redistribution of OSI dynamic routes";
          presence "true";
          uses route-map-metric-grouping;
        }
        container ip {
          presence "true";
          uses metric-route-map-grouping;
        }
        uses metric-route-map-grouping;
      }
    }
  }

  grouping metric-route-map-grouping {
    leaf metric {
      description
        "Metric for redistributed routes";
      type uint32 {
        range "0..4294967295";
      }
    }
    leaf route-map {
      description
        "Route map reference";
      type string;
    }
  }

  grouping route-map-metric-grouping {
    leaf route-map {
      description
        "Route map reference";
      type string;
    }
    leaf metric {
      description
        "Metric for redistributed routes";
      type uint32 {
        range "0..4294967295";
      }
    }
  }

  grouping redistribute-isis-grouping {
    choice osi-ip-choice {
      leaf ip {
        description
          "Redistribution of IP dynamic routes";
        type empty;
      }
      leaf clns {
        description
          "Redistribution of OSI dynamic routes";
        type empty;
      }
    }
    leaf routes {
      type enumeration {
        enum "level-1";
        enum "level-2";
        enum "level-1-2";
      }
    }
    uses metric-route-map-grouping;
  }

  grouping redistribute-ospf-non-vrf-grouping {
    container match {
      leaf internal {
        description
          "Redistribute OSPF internal routes";
        type empty;
      }
      leaf external {
        description
          "Redistribute OSPF external routes";
        type ios-types:redist-ospf-external-type;
      }
      leaf external2 {
        description
          "Redistribute OSPF external routes";
        type ios-types:redist-ospf-external-type;
      }
      leaf nssa-external {
        description
          "Redistribute OSPF NSSA external routes";
        type ios-types:redist-ospf-external-type;
      }
      uses metric-route-map-grouping;
    }
    uses metric-route-map-grouping;
  }

  // router bgp * / address-family * / segment-routing
  grouping address-family-segment-routing-grouping {
    container segment-routing {
       description
         "segment-routing";
       leaf mpls {
         description
           "mpls";
         type empty;
       }
     }
  }

  // router bgp * / address-family * / snmp
  grouping address-family-snmp-grouping {
    container snmp {
      description
        "Modify snmp parameters";
      presence "true";
      container context {
        description
          "Configure a SNMP context";
        list context_word {
          key "context_word";
          leaf context_word {
            description
              "Context Name";
            type string;
          }
        }
      }
    }
  }

  // router bgp * / address-family * / synchronization
  grouping address-family-synchronization-grouping {
    leaf synchronization {
      description
        "Perform IGP synchronization";
      type empty;
    }
  }

  // router bgp * / address-family * / table-map
  grouping address-family-table-map-grouping {
    container table-map {
      presence "true";
      description
        "Map external entry attributes into routing table";
      leaf name {
        description
          "WORD :: Route-map name";
        type string;
      }
      leaf filter {
        type empty;
      }
    }
  }

  grouping global-neighbor {
    uses neighbor-remote-as-grouping;
    uses neighbor-cluster-id-grouping;
    uses neighbor-description-grouping;
    uses neighbor-disable-connected-check-grouping;
    uses neighbor-ebgp-multihop-grouping;
    uses neighbor-fall-over-grouping;
    uses neighbor-ha-mode-grouping;
    uses neighbor-inherit-grouping;
    uses neighbor-local-as-grouping;
    uses neighbor-log-neighbor-changes-grouping;
    uses neighbor-password-grouping;
    uses neighbor-path-attribute-grouping;
    uses neighbor-shutdown-grouping;
    uses neighbor-timers-grouping;
    uses neighbor-transport-grouping;
    uses neighbor-ttl-security-grouping;
    uses neighbor-update-source-grouping;
    uses neighbor-version-grouping;
  }

  grouping global-peer-group {
    uses peer-group-peer-group-grouping;
    uses neighbor-cluster-id-grouping;
    uses neighbor-description-grouping;
    uses neighbor-disable-connected-check-grouping;
    uses neighbor-ebgp-multihop-grouping;
    uses neighbor-fall-over-grouping;
    uses neighbor-ha-mode-grouping;
    uses neighbor-inherit-grouping;
    uses neighbor-local-as-grouping;
    uses neighbor-log-neighbor-changes-grouping;
    uses neighbor-password-grouping;
    uses neighbor-path-attribute-grouping;
    uses peer-group-remote-as-grouping;
    uses neighbor-shutdown-grouping;
    uses neighbor-timers-grouping;
    uses neighbor-transport-grouping;
    uses neighbor-ttl-security-grouping;
    uses neighbor-update-source-grouping;
    uses neighbor-version-grouping;
  }

  grouping ipv4-unicast-neighbor {
    uses neighbor-activate-grouping;
    uses neighbor-additional-paths-grouping;
    uses neighbor-advertise-grouping;
    uses neighbor-advertise-map-grouping;
    uses neighbor-advertisement-interval-grouping;
    uses neighbor-aigp-grouping;
    uses neighbor-allow-policy-grouping;
    uses neighbor-allowas-in-grouping;
    uses neighbor-announce-grouping;
    uses neighbor-as-override-grouping;
    uses neighbor-capability-grouping;
    uses neighbor-default-originate-grouping;
    uses neighbor-distribute-list-grouping;
    uses neighbor-dmzlink-bw-grouping;
    uses neighbor-filter-list-grouping;
    uses neighbor-inherit-grouping;
    uses neighbor-maximum-prefix-grouping;
    uses neighbor-next-hop-self-grouping;
    uses neighbor-next-hop-unchanged-grouping;
    uses neighbor-peer-group-grouping;
    uses neighbor-prefix-list-grouping;
    uses neighbor-remove-private-as-grouping;
    uses neighbor-route-map-grouping;
    uses neighbor-route-reflector-client-grouping;
    uses neighbor-send-community-grouping;
    uses neighbor-send-label-grouping;
    uses neighbor-slow-peer-grouping;
    uses neighbor-soft-reconfiguration-grouping;
    uses neighbor-soo-grouping;
    uses neighbor-translate-update-grouping;
    uses neighbor-unsuppress-map-grouping;
    uses neighbor-weight-grouping;
  }

  grouping ipv4-multicast-neighbor {
    uses neighbor-activate-grouping;
    uses neighbor-additional-paths-grouping;
    uses neighbor-advertise-grouping;
    uses neighbor-advertise-map-grouping;
    uses neighbor-advertisement-interval-grouping;
    uses neighbor-aigp-grouping;
    uses neighbor-allow-policy-grouping;
    uses neighbor-allowas-in-grouping;
    uses neighbor-capability-grouping;
    uses neighbor-default-originate-grouping;
    uses neighbor-distribute-list-grouping;
    uses neighbor-dmzlink-bw-grouping;
    uses neighbor-filter-list-grouping;
    uses neighbor-inherit-grouping;
    uses neighbor-maximum-prefix-grouping;
    uses neighbor-next-hop-self-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping ipv4-flowspec-neighbor {
    uses neighbor-activate-grouping;
    uses neighbor-advertisement-interval-grouping;
    uses neighbor-allowas-in-grouping;
    uses neighbor-inherit-grouping;
    uses neighbor-maximum-prefix-grouping;
    uses neighbor-next-hop-self-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-weight-grouping;
  }

  grouping ipv4-mvpn-neighbor {
    uses neighbor-activate-grouping;
    uses neighbor-advertisement-interval-grouping;
    uses neighbor-allow-policy-grouping;
    uses neighbor-allowas-in-grouping;
    uses neighbor-filter-list-grouping;
    uses neighbor-inherit-grouping;
    uses neighbor-maximum-prefix-grouping;
    uses neighbor-next-hop-self-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping ipv4-mdt-neighbor {
    uses neighbor-activate-grouping;
    uses neighbor-advertisement-interval-grouping;
    uses neighbor-allow-policy-grouping;
    uses neighbor-allowas-in-grouping;
    uses neighbor-filter-list-grouping;
    uses neighbor-inherit-grouping;
    uses neighbor-maximum-prefix-grouping;
    uses neighbor-next-hop-self-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping ipv6-unicast-neighbor {
    uses neighbor-activate-grouping;
    uses neighbor-additional-paths-grouping;
    uses neighbor-advertise-grouping;
    uses neighbor-advertise-map-grouping;
    uses neighbor-aigp-grouping;
    uses neighbor-allow-policy-grouping;
    uses neighbor-allowas-in-grouping;
    uses neighbor-announce-grouping;
    uses neighbor-as-override-grouping;
    uses neighbor-capability-grouping;
    uses neighbor-default-originate-grouping;
    uses neighbor-dmzlink-bw-grouping;
    uses neighbor-filter-list-grouping;
    uses neighbor-inherit-grouping;
    uses neighbor-maximum-prefix-grouping;
    uses neighbor-next-hop-self-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-send-label-grouping;
    uses neighbor-slow-peer-grouping;
    uses neighbor-soft-reconfiguration-grouping;
    uses neighbor-soo-grouping;
    uses neighbor-translate-update-grouping;
    uses neighbor-unsuppress-map-grouping;
    uses neighbor-weight-grouping;
  }

  grouping ipv6-multicast-neighbor {
    uses neighbor-activate-grouping;
    uses neighbor-additional-paths-grouping;
    uses neighbor-advertise-grouping;
    uses neighbor-advertise-map-grouping;
    uses neighbor-advertisement-interval-grouping;
    uses neighbor-aigp-grouping;
    uses neighbor-allow-policy-grouping;
    uses neighbor-allowas-in-grouping;
    uses neighbor-capability-grouping;
    uses neighbor-default-originate-grouping;
    uses neighbor-distribute-list-grouping;
    uses neighbor-dmzlink-bw-grouping;
    uses neighbor-filter-list-grouping;
    uses neighbor-inherit-grouping;
    uses neighbor-maximum-prefix-grouping;
    uses neighbor-next-hop-self-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping ipv6-flowspec-neighbor {
    uses neighbor-activate-grouping;
    uses neighbor-advertisement-interval-grouping;
    uses neighbor-allowas-in-grouping;
    uses neighbor-inherit-grouping;
    uses neighbor-maximum-prefix-grouping;
    uses neighbor-next-hop-self-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-weight-grouping;
  } 

  grouping ipv6-mvpn-neighbor {
    uses neighbor-activate-grouping;
    uses neighbor-advertisement-interval-grouping;
    uses neighbor-allow-policy-grouping;
    uses neighbor-allowas-in-grouping;
    uses neighbor-filter-list-grouping;
    uses neighbor-inherit-grouping;
    uses neighbor-maximum-prefix-grouping;
    uses neighbor-next-hop-self-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping l2vpn-evpn-neighbor {
    uses neighbor-activate-grouping;
    uses neighbor-additional-paths-grouping;
    uses neighbor-advertise-grouping;
    uses neighbor-advertisement-interval-grouping;
    uses neighbor-allow-policy-grouping;
    uses neighbor-allowas-in-grouping;
    uses neighbor-distribute-list-grouping;
    uses neighbor-dmzlink-bw-grouping;
    uses neighbor-encap-grouping;
    uses neighbor-filter-list-grouping;
    uses neighbor-inherit-grouping;
    uses neighbor-maximum-prefix-grouping;
    uses neighbor-next-hop-self-grouping;
    uses neighbor-next-hop-unchanged-grouping;
    uses neighbor-peer-group-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping l2vpn-vpls-neighbor {
    uses neighbor-activate-grouping;
    uses neighbor-advertisement-interval-grouping;
    uses neighbor-allow-policy-grouping;
    uses neighbor-allowas-in-grouping;
    uses neighbor-capability-grouping;
    uses neighbor-inherit-grouping;
    uses neighbor-maximum-prefix-grouping;
    uses neighbor-next-hop-self-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;
  }

  grouping rtfilter-neighbor {
    uses neighbor-activate-grouping;
    uses neighbor-advertisement-interval-grouping;
    uses neighbor-allow-policy-grouping;
    uses neighbor-allowas-in-grouping;
    uses neighbor-capability-grouping;
    uses neighbor-default-originate-grouping;
    uses neighbor-inherit-grouping;
    uses neighbor-maximum-prefix-grouping;
    uses neighbor-next-hop-self-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-weight-grouping;
  }

  grouping vpnv4-unicast-neighbor {
    uses neighbor-activate-grouping;
    uses neighbor-advertise-grouping;
    uses neighbor-advertisement-interval-grouping;
    uses neighbor-allow-policy-grouping;
    uses neighbor-allowas-in-grouping;
    uses neighbor-capability-grouping;
    uses neighbor-distribute-list-grouping;
    uses neighbor-dmzlink-bw-grouping;
    uses neighbor-filter-list-grouping;
    uses neighbor-inherit-grouping;
    uses neighbor-maximum-prefix-grouping;
    uses neighbor-next-hop-self-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-send-label-grouping;
    uses neighbor-slow-peer-grouping;
    uses neighbor-soft-reconfiguration-grouping;
    uses neighbor-soo-grouping;
    uses neighbor-unsuppress-map-grouping;
    uses neighbor-weight-grouping;
  }

  grouping vpnv4-multicast-neighbor {
    uses neighbor-activate-grouping;
    uses neighbor-advertisement-interval-grouping;
    uses neighbor-allow-policy-grouping;
    uses neighbor-allowas-in-grouping;
    uses neighbor-capability-grouping;
    uses neighbor-distribute-list-grouping;
    uses neighbor-dmzlink-bw-grouping;
    uses neighbor-filter-list-grouping;
    uses neighbor-inherit-grouping;
    uses neighbor-maximum-prefix-grouping;
    uses neighbor-next-hop-self-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;  
  }

  grouping vpnv4-flowspec-neighbor {
    uses neighbor-activate-grouping;
    uses neighbor-advertisement-interval-grouping;
    uses neighbor-allowas-in-grouping;
    uses neighbor-inherit-grouping;
    uses neighbor-maximum-prefix-grouping;
    uses neighbor-next-hop-self-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-weight-grouping;  
  }

  grouping vpnv6-unicast-neighbor {
    uses neighbor-activate-grouping;
    uses neighbor-advertise-grouping;
    uses neighbor-advertisement-interval-grouping;
    uses neighbor-allow-policy-grouping;
    uses neighbor-allowas-in-grouping;
    uses neighbor-distribute-list-grouping;
    uses neighbor-dmzlink-bw-grouping;
    uses neighbor-filter-list-grouping;
    uses neighbor-inherit-grouping;
    uses neighbor-maximum-prefix-grouping;
    uses neighbor-next-hop-self-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;  
  }

  grouping vpnv6-multicast-neighbor {
    uses neighbor-activate-grouping;
    uses neighbor-advertisement-interval-grouping;
    uses neighbor-allow-policy-grouping;
    uses neighbor-allowas-in-grouping;
    uses neighbor-capability-grouping;
    uses neighbor-distribute-list-grouping;
    uses neighbor-dmzlink-bw-grouping;
    uses neighbor-filter-list-grouping;
    uses neighbor-inherit-grouping;
    uses neighbor-maximum-prefix-grouping;
    uses neighbor-next-hop-self-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-soo-grouping;
    uses neighbor-unsuppress-map-grouping;
    uses neighbor-weight-grouping;  
  }

  grouping vpnv6-flowspec-neighbor {
    uses neighbor-activate-grouping;
    uses neighbor-advertisement-interval-grouping;
    uses neighbor-allowas-in-grouping;
    uses neighbor-inherit-grouping;
    uses neighbor-maximum-prefix-grouping;
    uses neighbor-next-hop-self-grouping;
    uses neighbor-next-hop-unchanged-grouping;
    uses neighbor-remove-private-as-grouping;
    uses neighbor-route-map-grouping;
    uses neighbor-route-reflector-client-grouping;
    uses neighbor-send-community-grouping;
    uses neighbor-slow-peer-grouping;
    uses neighbor-soft-reconfiguration-grouping;
    uses neighbor-weight-grouping;  
  }

  grouping nsap-neighbor {
    uses neighbor-activate-grouping;
    uses neighbor-advertisement-interval-grouping;
    uses neighbor-allow-policy-grouping;
    uses neighbor-allowas-in-grouping;
    uses neighbor-capability-grouping;
    uses neighbor-default-originate-grouping;
    uses neighbor-dmzlink-bw-grouping;
    uses neighbor-filter-list-grouping;
    uses neighbor-inherit-grouping;
    uses neighbor-maximum-prefix-grouping;
    uses neighbor-next-hop-self-grouping;
    uses neighbor-next-hop-unchanged-grouping;
    uses neighbor-prefix-list-grouping;
    uses neighbor-remove-private-as-grouping;
    uses neighbor-route-map-grouping;
    uses neighbor-route-reflector-client-grouping;
    uses neighbor-send-community-grouping;
    uses neighbor-slow-peer-grouping;
    uses neighbor-soo-grouping;
    uses neighbor-weight-grouping;  
  }
  
  grouping vrf-ipv4-unicast-neighbor {
    uses peer-group-remote-as-grouping;
    uses neighbor-activate-grouping;
    uses neighbor-advertise-map-grouping;
    uses neighbor-advertisement-interval-grouping;
    uses neighbor-aigp-grouping;
    uses neighbor-allow-policy-grouping;
    uses neighbor-allowas-in-grouping;
    uses neighbor-announce-grouping;
    uses neighbor-as-override-grouping;
    uses neighbor-capability-grouping;
    uses neighbor-cluster-id-grouping;
    uses neighbor-default-originate-grouping;
    uses neighbor-description-grouping;
    uses neighbor-disable-connected-check-grouping;
    uses neighbor-distribute-list-grouping;
    uses neighbor-dmzlink-bw-grouping;
    uses neighbor-ebgp-multihop-grouping;
    uses neighbor-fall-over-grouping;
    uses neighbor-filter-list-grouping;
    uses neighbor-ha-mode-grouping;
    uses neighbor-inherit-grouping;
    uses neighbor-local-as-grouping;
    uses neighbor-log-neighbor-changes-grouping;
    uses neighbor-maximum-prefix-grouping;
    uses neighbor-next-hop-self-grouping;
    uses neighbor-next-hop-unchanged-grouping;
    uses neighbor-password-grouping;
    uses neighbor-path-attribute-grouping;
    uses neighbor-peer-group-grouping;
    uses neighbor-prefix-list-grouping;
    uses neighbor-remove-private-as-grouping;
    uses neighbor-route-map-grouping;
    uses neighbor-route-reflector-client-grouping;
    uses neighbor-send-community-grouping;
    uses neighbor-send-label-grouping;
    uses neighbor-shutdown-grouping;
    uses neighbor-slow-peer-grouping;
    uses neighbor-soft-reconfiguration-grouping;
    uses neighbor-soo-grouping;
    uses neighbor-timers-grouping;
    uses neighbor-translate-update-grouping;
    uses neighbor-transport-grouping;
    uses neighbor-ttl-security-grouping;
    uses neighbor-unsuppress-map-grouping;
    uses neighbor-update-source-grouping;
    uses neighbor-version-grouping;
    uses neighbor-weight-grouping;

  }
  
  grouping vrf-ipv4-multicast-neighbor {
    uses peer-group-remote-as-grouping;
    uses neighbor-activate-grouping;
    uses neighbor-advertise-map-grouping;
    uses neighbor-advertisement-interval-grouping;
    uses neighbor-aigp-grouping;
    uses neighbor-allow-policy-grouping;
    uses neighbor-allowas-in-grouping;
    uses neighbor-as-override-grouping;
    uses neighbor-capability-grouping;
    uses neighbor-cluster-id-grouping;
    uses neighbor-default-originate-grouping;
    uses neighbor-description-grouping;
    uses neighbor-disable-connected-check-grouping;
    uses neighbor-dmzlink-bw-grouping;
    uses neighbor-ebgp-multihop-grouping;
    uses neighbor-fall-over-grouping;
    uses neighbor-filter-list-grouping;
    uses neighbor-ha-mode-grouping;
    uses neighbor-inherit-grouping;
    uses neighbor-local-as-grouping;
    uses neighbor-log-neighbor-changes-grouping;
    uses neighbor-maximum-prefix-grouping;
    uses neighbor-next-hop-self-grouping;
    uses neighbor-next-hop-unchanged-grouping;
    uses neighbor-password-grouping;
    uses neighbor-path-attribute-grouping;
    uses neighbor-peer-group-grouping;
    uses neighbor-prefix-list-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-soo-grouping;
    uses neighbor-timers-grouping;
    uses neighbor-transport-grouping;
    uses neighbor-ttl-security-grouping;
    uses neighbor-unsuppress-map-grouping;
    uses neighbor-update-source-grouping;
    uses neighbor-version-grouping;
    uses neighbor-weight-grouping;
  }
  
  grouping vrf-ipv4-flowspec-neighbor {
    uses peer-group-remote-as-grouping;
    uses neighbor-activate-grouping;
    uses neighbor-advertisement-interval-grouping;
    uses neighbor-allowas-in-grouping;
    uses neighbor-cluster-id-grouping;
    uses neighbor-description-grouping;
    uses neighbor-disable-connected-check-grouping;
    uses neighbor-ebgp-multihop-grouping;
    uses neighbor-fall-over-grouping;
    uses neighbor-ha-mode-grouping;
    uses neighbor-inherit-grouping;
    uses neighbor-local-as-grouping;
    uses neighbor-log-neighbor-changes-grouping;
    uses neighbor-maximum-prefix-grouping;
    uses neighbor-next-hop-self-grouping;
    uses neighbor-next-hop-unchanged-grouping;
    uses neighbor-password-grouping;
    uses neighbor-path-attribute-grouping;
    uses neighbor-peer-group-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-timers-grouping;
    uses neighbor-transport-grouping;
    uses neighbor-ttl-security-grouping;
    uses neighbor-unsuppress-map-grouping;
    uses neighbor-update-source-grouping;
    uses neighbor-version-grouping;
    uses neighbor-weight-grouping;
  }
  
  grouping vrf-ipv6-unicast-neighbor {
    uses peer-group-remote-as-grouping;
    uses neighbor-activate-grouping;
    uses neighbor-advertise-map-grouping;
    uses neighbor-advertisement-interval-grouping;
    uses neighbor-aigp-grouping;
    uses neighbor-allow-policy-grouping;
    uses neighbor-allowas-in-grouping;
    uses neighbor-announce-grouping;
    uses neighbor-as-override-grouping;
    uses neighbor-capability-grouping;
    uses neighbor-cluster-id-grouping;
    uses neighbor-default-originate-grouping;
    uses neighbor-description-grouping;
    uses neighbor-disable-connected-check-grouping;
    uses neighbor-dmzlink-bw-grouping;
    uses neighbor-ebgp-multihop-grouping;
    uses neighbor-fall-over-grouping;
    uses neighbor-filter-list-grouping;
    uses neighbor-ha-mode-grouping;
    uses neighbor-inherit-grouping;
    uses neighbor-local-as-grouping;
    uses neighbor-log-neighbor-changes-grouping;
    uses neighbor-maximum-prefix-grouping;
    uses neighbor-next-hop-self-grouping;
    uses neighbor-next-hop-unchanged-grouping;
    uses neighbor-password-grouping;
    uses neighbor-path-attribute-grouping;
    uses neighbor-peer-group-grouping;
    uses neighbor-prefix-list-grouping;
    uses neighbor-remove-private-as-grouping;
    uses neighbor-route-map-grouping;
    uses neighbor-route-reflector-client-grouping;
    uses neighbor-send-community-grouping;
    uses neighbor-send-label-grouping;
    uses neighbor-shutdown-grouping;
    uses neighbor-slow-peer-grouping;
    uses neighbor-soft-reconfiguration-grouping;
    uses neighbor-soo-grouping;
    uses neighbor-timers-grouping;
    uses neighbor-translate-update-grouping;
    uses neighbor-transport-grouping;
    uses neighbor-ttl-security-grouping;
    uses neighbor-unsuppress-map-grouping;
    uses neighbor-update-source-grouping;
    uses neighbor-version-grouping;
    uses neighbor-weight-grouping;
  }

  grouping vrf-ipv6-multicast-neighbor {
    uses peer-group-remote-as-grouping;
    uses neighbor-activate-grouping;
    uses neighbor-advertisement-interval-grouping;
    uses neighbor-aigp-grouping;
    uses neighbor-allow-policy-grouping;
    uses neighbor-allowas-in-grouping;
    uses neighbor-as-override-grouping;
    uses neighbor-capability-grouping;
    uses neighbor-cluster-id-grouping;
    uses neighbor-default-originate-grouping;
    uses neighbor-description-grouping;
    uses neighbor-disable-connected-check-grouping;
    uses neighbor-dmzlink-bw-grouping;
    uses neighbor-ebgp-multihop-grouping;
    uses neighbor-fall-over-grouping;
    uses neighbor-filter-list-grouping;
    uses neighbor-ha-mode-grouping;
    uses neighbor-inherit-grouping;
    uses neighbor-local-as-grouping;
    uses neighbor-log-neighbor-changes-grouping;
    uses neighbor-maximum-prefix-grouping;
    uses neighbor-next-hop-self-grouping;
    uses neighbor-next-hop-unchanged-grouping;
    uses neighbor-password-grouping;
    uses neighbor-path-attribute-grouping;
    uses neighbor-peer-group-grouping;
    uses neighbor-prefix-list-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-soo-grouping;
    uses neighbor-timers-grouping;
    uses neighbor-transport-grouping;
    uses neighbor-ttl-security-grouping;
    uses neighbor-unsuppress-map-grouping;
    uses neighbor-update-source-grouping;
    uses neighbor-version-grouping;
    uses neighbor-weight-grouping;
  }
  
  grouping vrf-ipv6-flowspec-neighbor {
    uses peer-group-remote-as-grouping;
    uses neighbor-activate-grouping;
    uses neighbor-advertisement-interval-grouping;
    uses neighbor-allowas-in-grouping;
    uses neighbor-cluster-id-grouping;
    uses neighbor-description-grouping;
    uses neighbor-disable-connected-check-grouping;
    uses neighbor-ebgp-multihop-grouping;
    uses neighbor-fall-over-grouping;
    uses neighbor-ha-mode-grouping;
    uses neighbor-inherit-grouping;
    uses neighbor-local-as-grouping;
    uses neighbor-log-neighbor-changes-grouping;
    uses neighbor-maximum-prefix-grouping;
    uses neighbor-next-hop-self-grouping;
    uses neighbor-next-hop-unchanged-grouping;
    uses neighbor-password-grouping;
    uses neighbor-path-attribute-grouping;
    uses neighbor-peer-group-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-timers-grouping;
    uses neighbor-transport-grouping;
    uses neighbor-ttl-security-grouping;
    uses neighbor-update-source-grouping;
    uses neighbor-version-grouping;
    uses neighbor-weight-grouping;
  }

  grouping vrf-ipv4-unicast-peergroup {
    uses peer-group-peer-group-grouping;
    uses neighbor-activate-grouping;
    uses neighbor-advertise-map-grouping;
    uses neighbor-advertisement-interval-grouping;
    uses neighbor-aigp-grouping;
    uses neighbor-allow-policy-grouping;
    uses neighbor-allowas-in-grouping;
    uses neighbor-announce-grouping;
    uses neighbor-as-override-grouping;
    uses neighbor-capability-grouping;
    uses neighbor-cluster-id-grouping;
    uses neighbor-default-originate-grouping;
    uses neighbor-description-grouping;
    uses neighbor-disable-connected-check-grouping;
    uses neighbor-distribute-list-grouping;
    uses neighbor-dmzlink-bw-grouping;
    uses neighbor-ebgp-multihop-grouping;
    uses neighbor-fall-over-grouping;
    uses neighbor-filter-list-grouping;
    uses neighbor-ha-mode-grouping;
    uses neighbor-inherit-grouping;
    uses neighbor-local-as-grouping;
    uses neighbor-log-neighbor-changes-grouping;
    uses neighbor-maximum-prefix-grouping;
    uses neighbor-next-hop-self-grouping;
    uses neighbor-next-hop-unchanged-grouping;
    uses neighbor-password-grouping;
    uses neighbor-path-attribute-grouping;
    uses neighbor-prefix-list-grouping;
    uses peer-group-remote-as-grouping;
    uses neighbor-remove-private-as-grouping;
    uses neighbor-route-map-grouping;
    uses neighbor-route-reflector-client-grouping;
    uses neighbor-send-community-grouping;
    uses neighbor-send-label-grouping;
    uses neighbor-shutdown-grouping;
    uses neighbor-slow-peer-grouping;
    uses neighbor-soft-reconfiguration-grouping;
    uses neighbor-soo-grouping;
    uses neighbor-timers-grouping;
    uses neighbor-translate-update-grouping;
    uses neighbor-transport-grouping;
    uses neighbor-ttl-security-grouping;
    uses neighbor-unsuppress-map-grouping;
    uses neighbor-update-source-grouping;
    uses neighbor-version-grouping;
    uses neighbor-weight-grouping;
  }
  
  grouping vrf-ipv4-multicast-peergroup {
    uses peer-group-peer-group-grouping;
    uses neighbor-activate-grouping;
    uses neighbor-advertise-map-grouping;
    uses neighbor-advertisement-interval-grouping;
    uses neighbor-aigp-grouping;
    uses neighbor-allow-policy-grouping;
    uses neighbor-allowas-in-grouping;
    uses neighbor-as-override-grouping;
    uses neighbor-capability-grouping;
    uses neighbor-cluster-id-grouping;
    uses neighbor-default-originate-grouping;
    uses neighbor-description-grouping;
    uses neighbor-disable-connected-check-grouping;
    uses neighbor-dmzlink-bw-grouping;
    uses neighbor-ebgp-multihop-grouping;
    uses neighbor-fall-over-grouping;
    uses neighbor-filter-list-grouping;
    uses neighbor-ha-mode-grouping;
    uses neighbor-inherit-grouping;
    uses neighbor-local-as-grouping;
    uses neighbor-log-neighbor-changes-grouping;
    uses neighbor-maximum-prefix-grouping;
    uses neighbor-next-hop-self-grouping;
    uses neighbor-next-hop-unchanged-grouping;
    uses neighbor-password-grouping;
    uses neighbor-path-attribute-grouping;
    uses neighbor-prefix-list-grouping;
    uses peer-group-remote-as-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-soo-grouping;
    uses neighbor-timers-grouping;
    uses neighbor-transport-grouping;
    uses neighbor-ttl-security-grouping;
    uses neighbor-unsuppress-map-grouping;
    uses neighbor-update-source-grouping;
    uses neighbor-version-grouping;
    uses neighbor-weight-grouping;
  }
  
  grouping vrf-ipv4-flowspec-peergroup {
    uses peer-group-peer-group-grouping;
    uses neighbor-activate-grouping;
    uses neighbor-advertisement-interval-grouping;
    uses neighbor-allowas-in-grouping;
    uses neighbor-cluster-id-grouping;
    uses neighbor-description-grouping;
    uses neighbor-disable-connected-check-grouping;
    uses neighbor-ebgp-multihop-grouping;
    uses neighbor-fall-over-grouping;
    uses neighbor-ha-mode-grouping;
    uses neighbor-inherit-grouping;
    uses neighbor-local-as-grouping;
    uses neighbor-log-neighbor-changes-grouping;
    uses neighbor-maximum-prefix-grouping;
    uses neighbor-next-hop-self-grouping;
    uses neighbor-next-hop-unchanged-grouping;
    uses neighbor-password-grouping;
    uses neighbor-path-attribute-grouping;
    uses peer-group-remote-as-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-timers-grouping;
    uses neighbor-transport-grouping;
    uses neighbor-ttl-security-grouping;
    uses neighbor-unsuppress-map-grouping;
    uses neighbor-update-source-grouping;
    uses neighbor-version-grouping;
    uses neighbor-weight-grouping;
  }
  
  grouping vrf-ipv6-unicast-peergroup {
    uses peer-group-peer-group-grouping;
    uses neighbor-activate-grouping;
    uses neighbor-advertise-map-grouping;
    uses neighbor-advertisement-interval-grouping;
    uses neighbor-aigp-grouping;
    uses neighbor-allow-policy-grouping;
    uses neighbor-allowas-in-grouping;
    uses neighbor-announce-grouping;
    uses neighbor-as-override-grouping;
    uses neighbor-capability-grouping;
    uses neighbor-cluster-id-grouping;
    uses neighbor-default-originate-grouping;
    uses neighbor-description-grouping;
    uses neighbor-disable-connected-check-grouping;
    uses neighbor-dmzlink-bw-grouping;
    uses neighbor-ebgp-multihop-grouping;
    uses neighbor-fall-over-grouping;
    uses neighbor-filter-list-grouping;
    uses neighbor-ha-mode-grouping;
    uses neighbor-inherit-grouping;
    uses neighbor-local-as-grouping;
    uses neighbor-log-neighbor-changes-grouping;
    uses neighbor-maximum-prefix-grouping;
    uses neighbor-next-hop-self-grouping;
    uses neighbor-next-hop-unchanged-grouping;
    uses neighbor-password-grouping;
    uses neighbor-path-attribute-grouping;
    uses neighbor-prefix-list-grouping;
    uses peer-group-remote-as-grouping;
    uses neighbor-remove-private-as-grouping;
    uses neighbor-route-map-grouping;
    uses neighbor-route-reflector-client-grouping;
    uses neighbor-send-community-grouping;
    uses neighbor-send-label-grouping;
    uses neighbor-shutdown-grouping;
    uses neighbor-slow-peer-grouping;
    uses neighbor-soft-reconfiguration-grouping;
    uses neighbor-soo-grouping;
    uses neighbor-timers-grouping;
    uses neighbor-translate-update-grouping;
    uses neighbor-transport-grouping;
    uses neighbor-ttl-security-grouping;
    uses neighbor-unsuppress-map-grouping;
    uses neighbor-update-source-grouping;
    uses neighbor-version-grouping;
    uses neighbor-weight-grouping;
  }

  grouping vrf-ipv6-multicast-peergroup {
    uses peer-group-peer-group-grouping;
    uses neighbor-activate-grouping;
    uses neighbor-advertisement-interval-grouping;
    uses neighbor-aigp-grouping;
    uses neighbor-allow-policy-grouping;
    uses neighbor-allowas-in-grouping;
    uses neighbor-as-override-grouping;
    uses neighbor-capability-grouping;
    uses neighbor-cluster-id-grouping;
    uses neighbor-default-originate-grouping;
    uses neighbor-description-grouping;
    uses neighbor-disable-connected-check-grouping;
    uses neighbor-dmzlink-bw-grouping;
    uses neighbor-ebgp-multihop-grouping;
    uses neighbor-fall-over-grouping;
    uses neighbor-filter-list-grouping;
    uses neighbor-ha-mode-grouping;
    uses neighbor-inherit-grouping;
    uses neighbor-local-as-grouping;
    uses neighbor-log-neighbor-changes-grouping;
    uses neighbor-maximum-prefix-grouping;
    uses neighbor-next-hop-self-grouping;
    uses neighbor-next-hop-unchanged-grouping;
    uses neighbor-password-grouping;
    uses neighbor-path-attribute-grouping;
    uses neighbor-prefix-list-grouping;
    uses peer-group-remote-as-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-soo-grouping;
    uses neighbor-timers-grouping;
    uses neighbor-transport-grouping;
    uses neighbor-ttl-security-grouping;
    uses neighbor-unsuppress-map-grouping;
    uses neighbor-update-source-grouping;
    uses neighbor-version-grouping;
    uses neighbor-weight-grouping;
  }
  
  grouping vrf-ipv6-flowspec-peergroup {
    uses peer-group-peer-group-grouping;
    uses neighbor-activate-grouping;
    uses neighbor-advertisement-interval-grouping;
    uses neighbor-allowas-in-grouping;
    uses neighbor-cluster-id-grouping;
    uses neighbor-description-grouping;
    uses neighbor-disable-connected-check-grouping;
    uses neighbor-ebgp-multihop-grouping;
    uses neighbor-fall-over-grouping;
    uses neighbor-ha-mode-grouping;
    uses neighbor-inherit-grouping;
    uses neighbor-local-as-grouping;
    uses neighbor-log-neighbor-changes-grouping;
    uses neighbor-maximum-prefix-grouping;
    uses neighbor-next-hop-self-grouping;
    uses neighbor-next-hop-unchanged-grouping;
    uses neighbor-password-grouping;
    uses neighbor-path-attribute-grouping;
    uses peer-group-remote-as-grouping;
    uses neighbor-remove-private-as-grouping;
    uses neighbor-route-map-grouping;
    uses neighbor-route-reflector-client-grouping;
    uses neighbor-send-community-grouping;
    uses neighbor-shutdown-grouping;
    uses neighbor-slow-peer-grouping;
    uses neighbor-soft-reconfiguration-grouping;
    uses neighbor-timers-grouping;
    uses neighbor-transport-grouping;
    uses neighbor-ttl-security-grouping;
    uses neighbor-update-source-grouping;
    uses neighbor-version-grouping;
    uses neighbor-weight-grouping;
  }
  
  grouping ipv4-unicast-bgp {
    container bgp {
      uses bgp-additional-paths-grouping;
      uses bgp-advertise-best-external-grouping;
      uses bgp-aggregate-timer-grouping;
      uses bgp-bestpath-grouping;
      uses bgp-dampening-grouping;
      uses bgp-dmzlink-bw-grouping;
      uses bgp-inject-map-grouping;
      uses bgp-nexthop-grouping;
      uses bgp-recursion-grouping;
      uses bgp-redistribute-internal-grouping;
      uses bgp-route-map-grouping;
      uses bgp-scan-time-grouping;
      uses bgp-slow-peer-grouping;
      uses bgp-soft-reconfig-backup-grouping;
      uses bgp-suppress-inactive-grouping;
      uses bgp-update-group-grouping; 
    }
  }

  grouping ipv4-multicast-bgp {
    container bgp {
     uses bgp-additional-paths-grouping;
      uses bgp-aggregate-timer-grouping;
      uses bgp-dampening-grouping;
      uses bgp-dmzlink-bw-grouping;
      uses bgp-nexthop-grouping;
      uses bgp-redistribute-internal-grouping;
      uses bgp-route-map-grouping;
      uses bgp-scan-time-grouping;
      uses bgp-slow-peer-grouping;
      uses bgp-soft-reconfig-backup-grouping;
      uses bgp-update-group-grouping; 
    }
  }

  grouping ipv4-flowspec-bgp {
    container bgp {
      uses bgp-nexthop-grouping;
      uses bgp-route-map-grouping;
      uses bgp-scan-time-grouping;
      uses bgp-slow-peer-grouping;
    }
  }

  grouping ipv4-mvpn-bgp {
    container bgp {
      uses bgp-default-grouping;
      uses bgp-dmzlink-bw-grouping;
      uses bgp-nexthop-grouping;
      uses bgp-scan-time-grouping;
      uses bgp-slow-peer-grouping;
      uses bgp-soft-reconfig-backup-grouping;
    }
  }

  grouping ipv4-mdt-bgp {
    container bgp {
      uses bgp-dampening-grouping;
      uses bgp-dmzlink-bw-grouping;
      uses bgp-nexthop-grouping;
      uses bgp-scan-time-grouping;
      uses bgp-slow-peer-grouping;
      uses bgp-soft-reconfig-backup-grouping;
    }
  }

  grouping ipv6-unicast-bgp {
    container bgp {
      uses bgp-additional-paths-grouping;
      uses bgp-advertise-best-external-grouping;
      uses bgp-aggregate-timer-grouping;
      uses bgp-bestpath-grouping;
      uses bgp-dampening-grouping;
      uses bgp-dmzlink-bw-grouping;
      uses bgp-inject-map-grouping;
      uses bgp-nexthop-grouping;
      uses bgp-recursion-grouping;
      uses bgp-redistribute-internal-grouping;
      uses bgp-route-map-grouping;
      uses bgp-scan-time-grouping;
      uses bgp-slow-peer-grouping;
      uses bgp-soft-reconfig-backup-grouping;
      uses bgp-suppress-inactive-grouping;
      uses bgp-update-group-grouping; 
    }
  }

  grouping ipv6-multicast-bgp {
    container bgp {
      uses bgp-additional-paths-grouping;
      uses bgp-aggregate-timer-grouping;
      uses bgp-dampening-grouping;
      uses bgp-dmzlink-bw-grouping;
      uses bgp-nexthop-grouping;
      uses bgp-redistribute-internal-grouping;
      uses bgp-route-map-grouping;
      uses bgp-scan-time-grouping;
      uses bgp-slow-peer-grouping;
      uses bgp-soft-reconfig-backup-grouping;
      uses bgp-update-group-grouping; 
    }
  }

  grouping ipv6-flowspec-bgp {
    container bgp {
      uses bgp-nexthop-grouping;
      uses bgp-route-map-grouping;
      uses bgp-scan-time-grouping;
      uses bgp-slow-peer-grouping;
    }
  }

  grouping ipv6-mvpn-bgp {
    container bgp {
      uses bgp-default-grouping;
      uses bgp-dmzlink-bw-grouping;
      uses bgp-nexthop-grouping;
      uses bgp-scan-time-grouping;
      uses bgp-slow-peer-grouping;
      uses bgp-soft-reconfig-backup-grouping;
    }
  }
  
  grouping vpnv4-unicast-bgp {
    container bgp {
      uses bgp-additional-paths-grouping;
      uses bgp-advertise-best-external-grouping;
      uses bgp-aggregate-timer-grouping;
      uses bgp-bestpath-grouping;
      uses bgp-dampening-grouping;
      uses bgp-default-grouping;
      uses bgp-dmzlink-bw-grouping;
      uses bgp-nexthop-grouping;
      uses bgp-recursion-grouping;
      uses bgp-redistribute-internal-grouping;
      uses bgp-route-map-grouping;
      uses bgp-scan-time-grouping;
      uses bgp-slow-peer-grouping;
      uses bgp-soft-reconfig-backup-grouping;
      uses bgp-update-group-grouping; 
    }
  }

  grouping vpnv4-multicast-bgp {
    container bgp {
      uses bgp-aggregate-timer-grouping;
      uses bgp-dampening-grouping;
      uses bgp-default-grouping;
      uses bgp-dmzlink-bw-grouping;
      uses bgp-nexthop-grouping;
      uses bgp-redistribute-internal-grouping;
      uses bgp-route-map-grouping;
      uses bgp-scan-time-grouping;
      uses bgp-slow-peer-grouping;
      uses bgp-soft-reconfig-backup-grouping;
      uses bgp-update-group-grouping; 
    }
  }

  grouping vpnv4-flowspec-bgp {
    container bgp {
      uses bgp-nexthop-grouping;
      uses bgp-route-map-grouping;
      uses bgp-scan-time-grouping;
      uses bgp-slow-peer-grouping;
    }
  }

  grouping vpnv6-unicast-bgp {
    container bgp {
      uses bgp-additional-paths-grouping;
      uses bgp-advertise-best-external-grouping;
      uses bgp-aggregate-timer-grouping;
      uses bgp-bestpath-grouping;
      uses bgp-dampening-grouping;
      uses bgp-default-grouping;
      uses bgp-dmzlink-bw-grouping;
      uses bgp-nexthop-grouping;
      uses bgp-recursion-grouping;
      uses bgp-redistribute-internal-grouping;
      uses bgp-route-map-grouping;
      uses bgp-scan-time-grouping;
      uses bgp-slow-peer-grouping;
      uses bgp-soft-reconfig-backup-grouping;
     uses bgp-update-group-grouping; 
    }
  }

  grouping vpnv6-multicast-bgp {
    container bgp {
      uses bgp-aggregate-timer-grouping;
      uses bgp-dampening-grouping;
      uses bgp-default-grouping;
      uses bgp-dmzlink-bw-grouping;
      uses bgp-nexthop-grouping;
      uses bgp-redistribute-internal-grouping;
      uses bgp-route-map-grouping;
      uses bgp-scan-time-grouping;
      uses bgp-slow-peer-grouping;
      uses bgp-soft-reconfig-backup-grouping;
      uses bgp-update-group-grouping; 
    }
  }

  grouping vpnv6-flowspec-bgp {
    container bgp {
      uses bgp-nexthop-grouping;
      uses bgp-route-map-grouping;
      uses bgp-scan-time-grouping;
      uses bgp-slow-peer-grouping;
    }
  }

  grouping l2vpn-evpn-bgp {
    container bgp {
      uses bgp-additional-paths-grouping;
      uses bgp-default-grouping;
    }
  }

  grouping l2vpn-vpls-bgp {
    container bgp {
      uses bgp-default-grouping;
      uses bgp-nexthop-grouping;
      uses bgp-scan-time-grouping;
      uses bgp-slow-peer-grouping;
    }
  }

  grouping rtfilter-bgp {
    container bgp {
      uses bgp-nexthop-grouping;
      uses bgp-slow-peer-grouping;
    }
  }

  grouping nsap-bgp {
    container bgp {
      uses bgp-aggregate-timer-grouping;
      uses bgp-dampening-grouping;
      uses bgp-dmzlink-bw-grouping;
      uses bgp-nexthop-grouping;
      uses bgp-redistribute-internal-grouping;
      uses bgp-route-map-grouping;
      uses bgp-scan-time-grouping;
      uses bgp-slow-peer-grouping;
      uses bgp-soft-reconfig-backup-grouping;
    }
  }

  grouping vrf-ipv4-unicast-bgp {
    container bgp {
      uses bgp-additional-paths-grouping;
      uses bgp-advertise-best-external-grouping;
      uses bgp-aggregate-timer-grouping;
      uses bgp-bestpath-grouping;
      uses bgp-dampening-grouping;
      uses bgp-recursion-grouping;
      uses bgp-redistribute-internal-grouping;
      uses bgp-route-map-grouping;
      uses bgp-router-id-grouping;
      uses bgp-slow-peer-grouping;
      uses bgp-suppress-inactive-grouping;
    }
  }

  grouping vrf-ipv4-multicast-bgp {
    container bgp {
      uses bgp-additional-paths-grouping;
      uses bgp-aggregate-timer-grouping;
      uses bgp-dampening-grouping;
      uses bgp-redistribute-internal-grouping;
      uses bgp-route-map-grouping;
      uses bgp-slow-peer-grouping;
    }
  }

  grouping vrf-ipv6-unicast-bgp {
    container bgp {
      uses bgp-additional-paths-grouping;
      uses bgp-advertise-best-external-grouping;
      uses bgp-aggregate-timer-grouping;
      uses bgp-bestpath-grouping;
      uses bgp-dampening-grouping;
      uses bgp-recursion-grouping;
      uses bgp-redistribute-internal-grouping;
      uses bgp-route-map-grouping;
      uses bgp-router-id-grouping;
      uses bgp-slow-peer-grouping;
      uses bgp-suppress-inactive-grouping;
    }
  }

  grouping vrf-ipv6-multicast-bgp {
    container bgp {
      uses bgp-additional-paths-grouping;
      uses bgp-aggregate-timer-grouping;
      uses bgp-dampening-grouping;
      uses bgp-redistribute-internal-grouping;
      uses bgp-route-map-grouping;
      uses bgp-slow-peer-grouping;
    }
  }

  grouping ipv4-unicast-grouping{
    container ipv4-unicast {
      description
	"IPv4 Unicast address family";
      uses address-family-ipv4-aggregate-address-grouping;
      uses address-family-auto-summary-grouping;
      uses ipv4-unicast-bgp;
      uses address-family-default-information-grouping;
      uses address-family-default-metric-grouping;
      uses address-family-distance-grouping;
      uses address-family-distribute-list-grouping;
      uses address-family-maximum-paths-grouping;
      container peer-group {
	list neighbor {
	  description
	    "Specify a neighbor router";
	  must "count(*) > 1" {
	  }
	  key "id";
	  leaf id {
	    type string;
	  }
	  uses ipv4-unicast-neighbor;
	}
      }
      list neighbor {
	description
	  "Specify a neighbor router";
	must "count(*) > 1" {
	}
	key "id";
	leaf id {
	  type inet:ip-address;
	}
	uses ipv4-unicast-neighbor;
      }
      uses address-family-ipv4-network-grouping;
      uses address-family-redistribute-grouping;
      uses address-family-segment-routing-grouping;
      uses address-family-snmp-grouping;
      uses address-family-synchronization-grouping;
      uses address-family-table-map-grouping;
    }
  }

  grouping ipv4-multicast-grouping{
    container ipv4-multicast {
      description
	"IPv4 Multicast address family";
      uses address-family-ipv4-aggregate-address-grouping;
      uses address-family-auto-summary-grouping;
      uses ipv4-multicast-bgp;
      uses address-family-default-information-grouping;
      uses address-family-default-metric-grouping;
      uses address-family-distance-grouping;
      container peer-group {
	list neighbor {
	  description
	    "Specify a neighbor router";
	  must "count(*) > 1" {
	  }
	  key "id";
	  leaf id {
	    type string;
	  }
	  uses ipv4-multicast-neighbor;
	}
      }
      list neighbor {
	description
	  "Specify a neighbor router";
	must "count(*) > 1" {
	}
	key "id";
	leaf id {
	  type inet:ip-address;
	}
	uses ipv4-multicast-neighbor;
      }
      uses address-family-ipv4-network-grouping;
      uses address-family-redistribute-grouping;
      uses address-family-snmp-grouping;
      uses address-family-table-map-grouping;
    }
  }

  grouping ipv4-flowspec-grouping{
    container ipv4-flowspec {
      description
	"Ipv4 Flowspec address family";
      uses ipv4-flowspec-bgp;
      uses address-family-default-information-grouping;
      uses address-family-default-metric-grouping;
      uses address-family-maximum-paths-grouping;
      container peer-group {
	list neighbor {
	  description
	    "Specify a neighbor router";
	  must "count(*) > 1" {
	  }
	  key "id";
	  leaf id {
	    type string;
	  }
	  uses ipv4-flowspec-neighbor;
	}
      }
      list neighbor {
	description
	  "Specify a neighbor router";
	must "count(*) > 1" {
	}
	key "id";
	leaf id {
	  type inet:ip-address;
	}
	uses ipv4-flowspec-neighbor;
      }
      uses address-family-ipv4-network-grouping;
      uses address-family-snmp-grouping;
    }
  }

  grouping ipv4-mvpn-grouping{
    container ipv4-mvpn {
      description
	"IPv4 MVPN address family";
      uses ipv4-mvpn-bgp;
      uses address-family-default-information-grouping;
      container peer-group {
	list neighbor {
	  description
	    "Specify a neighbor router";
	  must "count(*) > 1" {
	  }
	  key "id";
	  leaf id {
	    type string;
	  }
	  uses ipv4-mvpn-neighbor;
	}
      }
      list neighbor {
	description
	  "Specify a neighbor router";
	must "count(*) > 1" {
	}
	key "id";
	leaf id {
	  type inet:ip-address;
	}
	uses ipv4-mvpn-neighbor;
      }
      uses address-family-snmp-grouping;
    }
  }

  grouping ipv4-mdt-grouping{
    container ipv4-mdt {
      description
	"IPv4 MDT address family";
      uses ipv4-mdt-bgp;
      uses address-family-default-information-grouping;
      container peer-group {
	list neighbor {
	  description
	    "Specify a neighbor router";
	  must "count(*) > 1" {
	  }
	  key "id";
	  leaf id {
	    type string;
	  }
	  uses ipv4-mdt-neighbor;
	}
      }
      list neighbor {
	description
	  "Specify a neighbor router";
	must "count(*) > 1" {
	}
	key "id";
	leaf id {
	  type inet:ip-address;
	}
	uses ipv4-mdt-neighbor;
      }
      uses address-family-snmp-grouping;
    }
  }

  grouping ipv6-unicast-grouping{
    container ipv6-unicast {
      description
	"IPv6 Unicast address family";
      uses address-family-ipv6-aggregate-address-grouping;
      uses ipv6-unicast-bgp;
      uses address-family-default-information-grouping;
      uses address-family-default-metric-grouping;
      uses address-family-distance-grouping;
      uses address-family-maximum-paths-grouping;
      container peer-group {
	list neighbor {
	  description
	    "Specify a neighbor router";
	  must "count(*) > 1" {
	  }
	  key "id";
	  leaf id {
	    type string;
	  }
	  uses ipv6-unicast-neighbor;
	}
      }
      list neighbor {
	description
	  "Specify a neighbor router";
	must "count(*) > 1" {
	}
	key "id";
	leaf id {
	  type inet:ip-address;
	}
	uses ipv6-unicast-neighbor;
      }
      uses address-family-ipv6-network-grouping;
      uses address-family-redistribute-grouping;
      uses address-family-snmp-grouping;
      uses address-family-synchronization-grouping;
      uses address-family-table-map-grouping;
    }
  }

  grouping ipv6-multicast-grouping{
    container ipv6-multicast {
      description
	"IPv6 Multicast address family";
      uses address-family-ipv6-aggregate-address-grouping;
      uses ipv6-multicast-bgp;
      uses address-family-distance-grouping;
      container peer-group {
	list neighbor {
	  description
	    "Specify a neighbor router";
	  must "count(*) > 1" {
	  }
	  key "id";
	  leaf id {
	    type string;
	  }
	  uses ipv6-multicast-neighbor;
	}
      }
      list neighbor {
	description
	  "Specify a neighbor router";
	must "count(*) > 1" {
	}
	key "id";
	leaf id {
	  type inet:ip-address;
	}
	uses ipv6-multicast-neighbor;
      }
      uses address-family-ipv6-network-grouping;
      uses address-family-redistribute-grouping;
      uses address-family-snmp-grouping;
    }
  }

  grouping ipv6-flowspec-grouping{
    container ipv6-flowspec {
      description
	"IPv6 Flowspec address family";
      uses address-family-ipv6-aggregate-address-grouping;
      uses ipv6-flowspec-bgp;
      uses address-family-default-information-grouping;
      uses address-family-default-metric-grouping;
      uses address-family-distance-grouping;
      container peer-group {
	list neighbor {
	  description
	    "Specify a neighbor router";
	  must "count(*) > 1" {
	  }
	  key "id";
	  leaf id {
	    type string;
	  }
	  uses ipv6-flowspec-neighbor;
	}
      }
      list neighbor {
	description
	  "Specify a neighbor router";
	must "count(*) > 1" {
	}
	key "id";
	leaf id {
	  type inet:ip-address;
	}
	uses ipv6-flowspec-neighbor;
      }
      uses address-family-ipv6-network-grouping;
      uses address-family-redistribute-grouping;
      uses address-family-snmp-grouping;
    }
  }

  grouping ipv6-mvpn-grouping{
    container ipv6-mvpn {
      description
	"IPv6 MVPN address family";
      uses ipv6-mvpn-bgp;
      uses address-family-default-information-grouping;
      container peer-group {
	list neighbor {
	  description
	    "Specify a neighbor router";
	  must "count(*) > 1" {
	  }
	  key "id";
	  leaf id {
	    type string;
	  }
	  uses ipv6-mvpn-neighbor;
	}
      }
      list neighbor {
	description
	  "Specify a neighbor router";
	must "count(*) > 1" {
	}
	key "id";
	leaf id {
	  type inet:ip-address;
	}
	uses ipv6-mvpn-neighbor;
      }
      uses address-family-snmp-grouping;
    }
  }

  grouping vpnv4-unicast-grouping{
    container vpnv4-unicast {
      description
	"VPNv4 Unicast address family";
      uses vpnv4-unicast-bgp;
      uses address-family-maximum-paths-grouping;
      container peer-group {
	list neighbor {
	  description
	    "Specify a neighbor router";
	  must "count(*) > 1" {
	  }
	  key "id";
	  leaf id {
	    type string;
	  }
	  uses vpnv4-unicast-neighbor;
	}
      }
      list neighbor {
	description
	  "Specify a neighbor router";
	must "count(*) > 1" {
	}
	key "id";
	leaf id {
	  type inet:ip-address;
	}
	uses vpnv4-unicast-neighbor;
      }
      uses address-family-ipv4-network-grouping;
      uses address-family-snmp-grouping;
    }
  }

  grouping vpnv4-multicast-grouping{
    container vpnv4-multicast {
      description
	"VPNv4 Multiicast address family";
      uses vpnv4-multicast-bgp;
      uses address-family-maximum-paths-grouping;
      container peer-group {
	list neighbor {
	  description
	    "Specify a neighbor router";
	  must "count(*) > 1" {
	  }
	  key "id";
	  leaf id {
	    type string;
	  }
	  uses vpnv4-multicast-neighbor;
	}
      }
      list neighbor {
	description
	  "Specify a neighbor router";
	must "count(*) > 1" {
	}
	key "id";
	leaf id {
	  type inet:ip-address;
	}
	uses vpnv4-multicast-neighbor;
      }
      uses address-family-snmp-grouping;
    }
  }

  grouping vpnv4-flowspec-grouping{
    container vpnv4-flowspec {
      description
	"VPNv4 Flowspec address family";
      uses vpnv4-flowspec-bgp;
      uses address-family-maximum-paths-grouping;
      container peer-group {
	list neighbor {
	  description
	    "Specify a neighbor router";
	  must "count(*) > 1" {
	  }
	  key "id";
	  leaf id {
	    type string;
	  }
	  uses vpnv4-flowspec-neighbor;
	}
      }
      list neighbor {
	description
	  "Specify a neighbor router";
	must "count(*) > 1" {
	}
	key "id";
	leaf id {
	  type inet:ip-address;
	}
	uses vpnv4-flowspec-neighbor;
      }
      uses address-family-snmp-grouping;
    }
  }

  grouping vpnv6-unicast-grouping{
    container vpnv6-unicast {
      description
	"VPNv6 Unicast address family";
      uses vpnv6-unicast-bgp;
      container peer-group {
	list neighbor {
	  description
	    "Specify a neighbor router";
	  must "count(*) > 1" {
	  }
	  key "id";
	  leaf id {
	    type string;
	  }
	  uses vpnv6-unicast-neighbor;
	}
      }
      list neighbor {
	description
	  "Specify a neighbor router";
	must "count(*) > 1" {
	}
	key "id";
	leaf id {
	  type inet:ip-address;
	}
	uses vpnv6-unicast-neighbor;
      }
      uses address-family-snmp-grouping;
    }
  }

  grouping vpnv6-multicast-grouping{
    container vpnv6-multicast {
      description
	"VPNv6 Multiicast address family";
      uses vpnv6-multicast-bgp;
      container peer-group {
	list neighbor {
	  description
	    "Specify a neighbor router";
	  must "count(*) > 1" {
	  }
	  key "id";
	  leaf id {
	    type string;
	  }
	  uses vpnv6-multicast-neighbor;
	}
      }
      list neighbor {
	description
	  "Specify a neighbor router";
	must "count(*) > 1" {
	}
	key "id";
	leaf id {
	  type inet:ip-address;
	}
	uses vpnv6-multicast-neighbor;
      }
      uses address-family-snmp-grouping;
    }
  }

  grouping vpnv6-flowspec-grouping{
    container vpnv6-flowspec {
      description
	"VPNv6 Flowspec address family";
      uses vpnv6-flowspec-bgp;
      uses address-family-maximum-paths-grouping;
      container peer-group {
	list neighbor {
	  description
	    "Specify a neighbor router";
	  must "count(*) > 1" {
	  }
	  key "id";
	  leaf id {
	    type string;
	  }
	  uses vpnv6-flowspec-neighbor;
	}
      }
      list neighbor {
	description
	  "Specify a neighbor router";
	must "count(*) > 1" {
	}
	key "id";
	leaf id {
	  type inet:ip-address;
	}
	uses vpnv6-flowspec-neighbor;
      }
      uses address-family-snmp-grouping;
    }
  }

  grouping l2vpn-vpls-grouping {
    container l2vpn-vpls {
      if-feature ios-features:l2vpn;
      description 
	"L2VPN VPLS address family";
      uses l2vpn-vpls-bgp;
      uses address-family-default-information-grouping;
      container peer-group {
	list neighbor {
	  description
	    "Specify a neighbor router";
	  must "count(*) > 1" {
	  }
	  key "id";
	  leaf id {
	    type string;
	  }
	  uses l2vpn-vpls-neighbor;
	}
      }
      list neighbor {
	description
	  "Specify a neighbor router";
	must "count(*) > 1" {
	}
	key "id";
	leaf id {
	  type inet:ip-address;
	}
	uses l2vpn-vpls-neighbor;
      }
      uses address-family-snmp-grouping;
    }
  }

  grouping l2vpn-evpn-grouping {
    container l2vpn-evpn {
      if-feature ios-features:l2vpn;
      description 
	"L2VPN EVPN address family";
      uses l2vpn-evpn-bgp;
      uses address-family-default-information-grouping;
      uses address-family-default-metric-grouping;
      uses address-family-maximum-paths-grouping;
      container peer-group {
	list neighbor {
	  description
	    "Specify a neighbor router";
	  must "count(*) > 1" {
	  }
	  key "id";
	  leaf id {
	    type string;
	  }
	  uses l2vpn-evpn-neighbor;
	}
      }
      list neighbor {
	description
	  "Specify a neighbor router";
	must "count(*) > 1" {
	}
	key "id";
	leaf id {
	  type inet:ip-address;
	}
	uses l2vpn-evpn-neighbor;
      }
      uses l2vpn-vpls-neighbor;
      uses address-family-ipv4-network-grouping;
      uses address-family-snmp-grouping;
    }
  }

  grouping nsap-grouping {
    container nsap {
      description
	"NSAP address family";
      uses nsap-bgp;
      uses address-family-default-information-grouping;
      uses address-family-default-metric-grouping;
      uses address-family-maximum-paths-grouping;
      container peer-group {
	list neighbor {
	  description
	    "Specify a neighbor router";
	  must "count(*) > 1" {
	  }
	  key "id";
	  leaf id {
	    type string;
	  }
	  uses nsap-neighbor;
	}
      }
      list neighbor {
	description
	  "Specify a neighbor router";
	must "count(*) > 1" {
	}
	key "id";
	leaf id {
	  type inet:ip-address;
	}
	uses nsap-neighbor;
      }
      uses address-family-nsap-network-grouping;
      uses address-family-snmp-grouping;
    }
  }

  grouping rtfilter-grouping {
    container rtfilter {
      description
	"RT-Filter address family";
      uses rtfilter-bgp;
      uses address-family-maximum-paths-grouping;
      container peer-group {
	list neighbor {
	  description
	    "Specify a neighbor router";
	  must "count(*) > 1" {
	  }
	  key "id";
	  leaf id {
	    type string;
	  }
	  uses rtfilter-neighbor;
	}
      }
      list neighbor {
	description
	  "Specify a neighbor router";
	must "count(*) > 1" {
	}
	key "id";
	leaf id {
	  type inet:ip-address;
	}
	uses rtfilter-neighbor;
      }
      uses address-family-snmp-grouping;
    }
  }
  
  grouping vrf-ipv4-unicast-grouping {
    container ipv4-unicast {
      description 
	"IPv4 Unicast VRF address family";
      uses address-family-advertise-grouping;
      uses address-family-ipv4-aggregate-address-grouping;
      uses vrf-ipv4-unicast-bgp;
      uses address-family-default-information-grouping;
      uses address-family-default-metric-grouping;
      uses address-family-distance-grouping;
      uses address-family-distribute-list-grouping;
      uses address-family-vrf-import-grouping;
      uses address-family-maximum-paths-grouping;
      container peer-group {
        list neighbor {
	  description
	    "Specify a neighbor router";
	  must "count(*) > 1" {
	  }
	  key "id";
	  leaf id {
	    type string;
	  }
	  uses vrf-ipv4-unicast-peergroup;
	}
      }
      list neighbor {
	description
	  "Specify a neighbor router";
	must "count(*) > 1" {
	}
	key "id";
	leaf id {
	  type inet:ip-address;
	}
        uses vrf-ipv4-unicast-neighbor;
      }
      uses address-family-vrf-ipv4-network-grouping;
      uses address-family-redistribute-grouping;
      uses address-family-snmp-grouping;
      uses address-family-synchronization-grouping;
      uses address-family-table-map-grouping;
    }
  }

  grouping vrf-ipv4-multicast-grouping {
    container ipv4-multicast {
      description 
	"IPv4 Multicast VRF address family";
      uses address-family-ipv4-aggregate-address-grouping;
      uses vrf-ipv4-multicast-bgp;
      uses address-family-default-information-grouping;
      uses address-family-default-metric-grouping;
      uses address-family-distance-grouping;
      uses address-family-vrf-import-grouping;
      container peer-group {
	list neighbor {
	  description
	    "Specify a neighbor router";
	  must "count(*) > 1" {
	  }
	  key "id";
	  leaf id {
	    type string;
	  }
	  uses vrf-ipv4-multicast-peergroup;
	}
      }
      list neighbor {
	description
	  "Specify a neighbor router";
	must "count(*) > 1" {
	}
	key "id";
	leaf id {
	  type inet:ip-address;
	}
	uses vrf-ipv4-multicast-neighbor;
      }
      uses address-family-vrf-ipv4-network-grouping;
      uses address-family-redistribute-grouping;
      uses address-family-snmp-grouping;
      uses address-family-table-map-grouping;
    }
  }

  grouping vrf-ipv4-flowspec-grouping {
    container ipv4-flowspec {
      description 
	"IPv4 Flowspec VRF address family";
      container bgp {
	uses bgp-route-map-grouping;
	uses bgp-slow-peer-grouping;
      }
      uses address-family-default-information-grouping;
      uses address-family-default-metric-grouping;
      uses address-family-vrf-import-grouping;
      uses address-family-maximum-paths-grouping;
      container peer-group {
	list neighbor {
	  description
	    "Specify a neighbor router";
	  must "count(*) > 1" {
	  }
	  key "id";
	  leaf id {
	    type string;
	  }
	  uses vrf-ipv4-flowspec-peergroup;
	}
      }
      list neighbor {
	description
	  "Specify a neighbor router";
	must "count(*) > 1" {
	}
        key "id";
        leaf id {
	    type inet:ip-address;
        }
        uses vrf-ipv4-flowspec-neighbor;
      }
      uses address-family-vrf-ipv4-network-grouping;
      uses address-family-snmp-grouping;

    }
  }

  grouping vrf-ipv4-mvpn-grouping {
    container ipv4-mvpn {
      description 
	"IPv4 MVPN VRF address family";
      container bgp {
	uses bgp-dampening-grouping;
      }
    }
  }

  grouping vrf-ipv6-unicast-grouping {
    container ipv6-unicast {
      description 
	"IPv6 Unicast VRF address family";
      uses address-family-advertise-grouping;
      uses address-family-ipv6-aggregate-address-grouping;
      uses vrf-ipv6-unicast-bgp;
      uses address-family-default-information-grouping;
      uses address-family-default-metric-grouping;
      uses address-family-distance-grouping;
      uses address-family-vrf-import-grouping;
      uses address-family-maximum-paths-grouping;
      container peer-group {
        list neighbor {
	  description
	    "Specify a neighbor router";
	  must "count(*) > 1" {
	  }
	  key "id";
	  leaf id {
	    type string;
	  }
	  uses vrf-ipv6-unicast-peergroup;
	}
      }
      list neighbor {
	description
	  "Specify a neighbor router";
	must "count(*) > 1" {
	}
	key "id";
	leaf id {
	  type inet:ip-address;
	}
	uses vrf-ipv6-unicast-neighbor;
      }
      uses address-family-vrf-ipv6-network-grouping;
      uses address-family-redistribute-grouping;
      uses address-family-snmp-grouping;
      uses address-family-synchronization-grouping;
      uses address-family-table-map-grouping;
    }
  }

  grouping vrf-ipv6-multicast-grouping {
    container ipv6-multicast {
      description 
	"IPv6 Multicast VRF address family";
      uses address-family-ipv6-aggregate-address-grouping;
      uses vrf-ipv6-multicast-bgp;
      uses address-family-distance-grouping;
      uses address-family-vrf-import-grouping;
      container peer-group {
	list neighbor {
	  description
	    "Specify a neighbor router";
	  must "count(*) > 1" {
	  }
	  key "id";
	  leaf id {
	    type string;
	  }
	  uses vrf-ipv6-multicast-peergroup;
	}
      }
      list neighbor {
	description
	  "Specify a neighbor router";
	must "count(*) > 1" {
	}
	key "id";
	leaf id {
	  type inet:ip-address;
	}
	uses vrf-ipv6-multicast-neighbor;
      }
      uses address-family-vrf-ipv6-network-grouping;
      uses address-family-redistribute-grouping;
      uses address-family-snmp-grouping;
    }
  }

  grouping vrf-ipv6-flowspec-grouping {
    container ipv6-flowspec {
      description 
	"IPv6 Flowspec VRF address family";
      uses address-family-ipv6-aggregate-address-grouping;
      container bgp {
	uses bgp-route-map-grouping;
	uses bgp-slow-peer-grouping;
      }
      uses address-family-default-information-grouping;
      uses address-family-default-metric-grouping;
      uses address-family-distance-grouping;
      uses address-family-vrf-import-grouping;
      uses address-family-maximum-paths-grouping;
      container peer-group {
	list neighbor {
	  description
	    "Specify a neighbor router";
	  must "count(*) > 1" {
	  }
	  key "id";
	  leaf id {
	    type string;
	  }
	  uses vrf-ipv6-flowspec-peergroup;
        }
      }
      list neighbor {
	description
	  "Specify a neighbor router";
	must "count(*) > 1" {
	}
	key "id";
	leaf id {
	  type inet:ip-address;
	}
	uses vrf-ipv6-flowspec-neighbor;
      }
      uses address-family-vrf-ipv6-network-grouping;
      uses address-family-redistribute-grouping;
      uses address-family-snmp-grouping;
    }
  }

  grouping vrf-ipv6-mvpn-grouping {
    container ipv6-mvpn {
      description 
	"IPv6 Unicast VRF address family";
      container bgp {
	uses bgp-dampening-grouping;
      }
    }
  }

  grouping address-family-no-vrf-grouping {
    container no-vrf {
      list ipv4 {
        description
          "Address family";
        key "af-name";
        leaf af-name {
          type ios-types:bgp_ipv4_af_type;
        }
	uses ipv4-unicast-grouping;
      }
      list ipv6 {
        description
          "Address family";
        key "af-name";
        leaf af-name {
          type ios-types:bgp_ipv6_af_type;
        }
	uses ipv6-unicast-grouping;
      }
      // router bgp * / address-family vpnv4
      list vpnv4 {
        description
          "Address family";
        key "af-name";
        leaf af-name {
          type enumeration {
            enum "unicast" {
            }
            enum "multicast" {
            }
            enum "flowspec" {
            }
          }
        }
	uses vpnv4-unicast-grouping;
      }
      // router bgp * / address-family vpnv6
      list vpnv6 {
        description
          "Address family";
        key "af-name";
        leaf af-name {
          type enumeration {
            enum "unicast" {
            }
            enum "multicast" {
            }
            enum "flowspec" {
            }
          }
        }
	uses vpnv6-unicast-grouping;
      }
      // router bgp * / address-family nsap
      list nsap {
        description
          "Address family";
        key "af-name";
        leaf af-name {
          type enumeration {
            enum "unicast" {
            }
          }
        }
	uses nsap-grouping;
      }
      // router bgp * / address-family l2vpn
      list l2vpn {
        if-feature ios-features:l2vpn;
        description
          "Address family";
        key "af-name";
        leaf af-name {
          type enumeration {
            enum "evpn" {
            }
            enum "vpls" {
            }
          }
        }
	uses l2vpn-evpn-grouping;
	uses l2vpn-vpls-grouping;
      }
      // router bgp * / address-family rtfilter
      list rtfilter {
        description
          "Address family";
        key "af-name";
        leaf af-name {
          type enumeration {
            enum "unicast" {
            }
          }
        }
	uses rtfilter-grouping;
      }
    }
  }

  grouping ip-community-list-standard-grouping {
    container deny {
      description
        "Specify community to reject";
      leaf-list deny-list {
        type union {
          type ios-types:community-number-type;
          type ios-types:community-well-known-type;
        }
      }
    }
    container permit {
      description
        "Specify community to accept";
      leaf-list permit-list {
        type union {
          type ios-types:community-number-type;
          type ios-types:community-well-known-type;
        }
      }
    }
  }

  grouping ip-community-list-expanded-grouping {
    container deny {
      description
        "Specify community to reject";
      leaf-list deny-list {
        ordered-by user;
        type string;
      }
    }
    container permit {
      description
        "Specify community to accept";
      leaf-list permit-list {
        ordered-by user;
        type string;
      }
    }
  }

  grouping ip-extcommunity-list-standard-grouping {
    container deny {
      description
        "Specify community to reject";
      list rt {
        description
          "Route Target extended community";
        key "name";
        leaf name {
          type string;
        }
      }
      list soo {
        description
          "Site-of-Origin extended community";
        key "name";
        leaf name {
          type string;
        }
      }
      list vpn-distinguisher {
        description
          "VPN Distinguisher extcomm";
        key "name";
        leaf name {
          type string;
        }
      }
    }
    container permit {
      description
        "Specify community to accept";
      list rt {
        description
          "Route Target extended community";
        key "name";
        leaf name {
          type string;
        }
      }
      list soo {
        description
          "Site-of-Origin extended community";
        key "name";
        leaf name {
          type string;
        }
      }
      list vpn-distinguisher {
        description
          "VPN Distinguisher extcomm";
        key "name";
        leaf name {
          type string;
        }
      }
    }
  }


  grouping config-ip-community-list-grouping {
    container community-list {
      description
        "Add a community list entry";
      list number-standard {
        key "no";
        leaf no {
          type uint16 {
            range "1..99";
          }
        }
        uses ip-community-list-standard-grouping;
      }
      list number-expanded {
        key "no";
        leaf no {
          type uint16 {
            range "100..500";
          }
        }
        uses ip-community-list-expanded-grouping;
      }
      list expanded {
        description
          "Add an expanded community-list entry";
        key "name";
        leaf name {
          type string;
        }
        uses ip-community-list-expanded-grouping;
      }
      list standard {
        description
          "Add a standard community-list entry";
        key "name";
        leaf name {
          type string;
        }
        uses ip-community-list-standard-grouping;
      }
    }
  }

  grouping config-ip-extcommunity-list-grouping {
    container extcommunity-list {
      description
        "Extended a community list entry";
      list number-standard {
        key "no";
        leaf no {
          type uint16 {
            range "1..99";
          }
        }
        uses ip-extcommunity-list-standard-grouping;
      }
      list number-expanded {
        key "no";
        leaf no {
          type uint16 {
            range "100..500";
          }
        }
        uses ip-community-list-expanded-grouping;
      }
      list expanded {
        description
          "Extended an expanded community-list entry";
        key "name";
        leaf name {
          type string;
        }
        uses ip-community-list-expanded-grouping;
      }
      list standard {
        description
          "Extended a standard community-list entry";
        key "name";
        leaf name {
          type string;
        }
        uses ip-extcommunity-list-standard-grouping;
      }
    }
  }

  grouping config-ip-as-path-grouping {
    // ip as-path access-list *
    list access-list {
      description
        "Specify an access list number";
      key "name";
      leaf name {
        type uint16 {
          range "1..500";
        }
      }
      uses ip-community-list-expanded-grouping;
    }
  }

  grouping config-bgp-grouping {
    list bgp { 
      description
        "Border Gateway Protocol (BGP)";
      key "id";
      max-elements "1";
      leaf id {
        type ios-types:bgp-as-number-type;
      }
     
      container bgp {
	uses global-bgp-grouping;
      }

      container peer-group {
	list neighbor {
	  description
	    "Specify a neighbor router";
	  must "count(*) > 1" {
	  }
	  key "id";
	  leaf id {
	    type string;
	  }
	  uses global-peer-group;
	}
      }

      list neighbor {
	description
	  "Specify a neighbor router";
	must "count(*) > 1" {
	}
	key "id";
	leaf id {
	  type inet:ip-address;
	}
	uses global-neighbor;
      }

      // router bgp * / address-family
      container address-family {
        description
          "Enter Address Family command mode";
        // router bgp * / address-family ipv4 vrf
        container with-vrf {
          list ipv4 {
            description
              "Address family";
            key "af-name";
            leaf af-name {
              type ios-types:bgp_ipv4_af_type;
            }
            // router bgp * / address-family ipv4 vrf *
            list vrf {
              key "name";
              leaf name {
                type string;
              }
              uses vrf-ipv4-unicast-grouping;
              uses vrf-ipv4-multicast-grouping;                                                         
              uses vrf-ipv4-flowspec-grouping;                                                          
              uses vrf-ipv4-mvpn-grouping;
            }
          }
          // router bgp * / address-family ipv6
          list ipv6 {
            description
              "Address family";
            key "af-name";
            leaf af-name {
              type ios-types:bgp_ipv6_af_type;
            }
            list vrf {
              key "name";
              leaf name {
                type string;
              }
              uses vrf-ipv6-unicast-grouping;
              uses vrf-ipv6-multicast-grouping;                                                         
              uses vrf-ipv6-flowspec-grouping;                                                          
              uses vrf-ipv6-mvpn-grouping; 
            }
          }
        }
        container no-vrf {
          list ipv4 {
            description
              "Address family";
            key "af-name";
            leaf af-name {
              type ios-types:bgp_ipv4_af_type;
            }
            uses ipv4-unicast-grouping;
            uses ipv4-multicast-grouping;                                                             
            uses ipv4-flowspec-grouping;                                                              
            uses ipv4-mvpn-grouping;                                                                  
            uses ipv4-mdt-grouping;
          }
          list ipv6 {
            description
              "Address family";
            key "af-name";
            leaf af-name {
              type ios-types:bgp_ipv6_af_type;
            }
            uses ipv6-unicast-grouping;
            uses ipv6-multicast-grouping;                                                             
            uses ipv6-flowspec-grouping;                                                              
            uses ipv6-mvpn-grouping;
          }
          // router bgp * / address-family vpnv4
          list vpnv4 {
            description
              "Address family";
            key "af-name";
            leaf af-name {
              type enumeration {
                enum "unicast" {
                }
                enum "multicast" {
                }
                enum "flowspec" {
                }
              }
            }
            uses vpnv4-unicast-grouping;
            uses vpnv4-multicast-grouping;                                                            
            uses vpnv4-flowspec-grouping; 
          }
          // router bgp * / address-family vpnv6
          list vpnv6 {
            description
              "Address family";
            key "af-name";
            leaf af-name {
              type enumeration {
                enum "unicast" {
                }
                enum "multicast" {
                }
                enum "flowspec" {
                }
              }
            }
            uses vpnv6-unicast-grouping;
            uses vpnv6-multicast-grouping;                                                            
            uses vpnv6-flowspec-grouping; 
          }
          // router bgp * / address-family nsap
          list nsap {
            description
              "Address family";
            key "af-name";
            leaf af-name {
              type enumeration {
                enum "unicast" {
                }
              }
            }
	    uses nsap-grouping;
          }
          // router bgp * / address-family l2vpn
          list l2vpn {
            if-feature ios-features:l2vpn;
            description
              "Address family";
            key "af-name";
            leaf af-name {
              type enumeration {
                enum "evpn" {
                }
                enum "vpls" {
                }
              }
            }
            uses l2vpn-evpn-grouping;                                                                 
            uses l2vpn-vpls-grouping; 
          }
          // router bgp * / address-family rtfilter
          list rtfilter {
            description
              "Address family";
            key "af-name";
            leaf af-name {
              type enumeration {
                enum "unicast" {
                }
              }
            }
            uses rtfilter-grouping;
          }
        }
      }

      // router bgp * / template
      container template {
        description
          "Enter template command mode";
        list peer-policy {
          description
            "Template configuration for policy parameters";
          key "name";
          leaf name {
            type string;
          }
          list route-map {
            description
              "Apply route map to neighbor";
            key "name";
            leaf name {
              type string;
            }
            leaf in {
              description
                "Apply map to incoming routes";
              type empty;
            }
            leaf out {
              description
                "Apply map to outgong routes";
              type empty;
            }
          }
          list  filter-list {
            description "Establish BGP filters";
            key "filter-range";
            leaf filter-range {
              description "AS path access list";
              type uint16 {
                range "1..500";
              }
            }
            leaf in {
              description "Filter incoming routes";
              type empty;
            }
            leaf out {
              description "Filter outgoing routes";
              type empty;
            }
          }
          container inherit {
            description "Inherit a template";
            container peer-policy {
              list template {
                key "name";
                leaf name {
                  description "Template name";
                  type string;
                }
                leaf range {
                  description "Sequence number";
                  type uint16 {
                    range "1..65535";
                  }
                }
              }
            }
          }
          container encap {
            description 
              "Preferred Encapsulation for Neighbor";      
            choice encap-choice {
              leaf mpls {
                description 
                  "Neighbor Prefers MPLS";      
                type empty;
              }
              leaf vxlan {
                description
                  "Neighbor Prefers VxLAN";      
                type empty;
              }
            }
          }
        }
        list peer-session {
          description
            "Template configuration for session parameters";
          key "name";
          leaf name {
            type string;
          }
          container ha-mode {
            description
              "high availability mode";
            container graceful-restart {
              description
                "graceful-restart for this peer";
              presence "true";
              leaf disable {
                description
                  "disable graceful-restart";
                type empty;
              }
            }
          }

          container password {
            description "Set a password";
            list password-range {
              key "encruption-type-range";
              leaf encruption-type-range {
                description "Encryption type (0 to disable encryption, 7 for proprietary)";
                type uint8 {
                  range "0..7";
                }
              }
              leaf password {
                description "The password";
                type string;
              }
            }
            leaf password {
              description "The password";
              type string;
            }
          }
          leaf remote-as {
            description "Specify a BGP neighbor";
            type ios-types:bgp-as-number-type;
          }
          container update-source {
            description "Source of routing updates";
            uses ios-ifc:interface-grouping;
          }
          leaf version {
            description "Set the BGP version to match a neighbor";
            type uint8 {
              range "4";
            }
          }
        }
      }
      // router bgp * / timers
      container timers {
        description
          "Adjust routing timers";
        container bgp {
          description
            "BGP timers";
          leaf keepalive-interval {
	    default 60;
            type uint16 {
              range "0..65535";
            }
          }
          leaf holdtime {
	    default 180;
            type uint16 {
              range "0..65535";
            }
          }
          leaf minimum-neighbor-hold {
            type uint16 {
              range "0..65535";
            }
          }
        }
      }
      container scope {
        container global {
          presence true;
          container peer-group {
            list neighbor {
              description
                "Specify a neighbor router";
              must "count(*) > 1" {
              }
              key "id";
              leaf id {
                type string;
              }
              uses neighbor-remote-as-grouping;
              uses neighbor-peer-group-grouping;
              uses neighbor-description-grouping;
              uses neighbor-password-grouping;
              uses neighbor-update-source-grouping;
              uses neighbor-version-grouping;
            }
          }
          list neighbor {
              description
                "Specify a neighbor router";
              must "count(*) > 1" {
              }
              key "id";
              leaf id {
                type inet:ip-address;
              }
              uses neighbor-remote-as-grouping;
              uses neighbor-peer-group-grouping;
              uses neighbor-description-grouping;
              uses neighbor-password-grouping;
              uses neighbor-update-source-grouping;
              uses neighbor-version-grouping;
          }
          container address-family {
            description
              "Enter Address Family command mode";
            // router bgp * / address-family ipv4 vrf
            uses address-family-no-vrf-grouping;
          }
        }
        list vrf {
              key "id";
              leaf id {
                type union {
                  type inet:ipv4-address;
                  type inet:ipv6-address;
                  type string;
                }
              }
          container peer-group {
            list neighbor {
              description
                "Specify a neighbor router";
              must "count(*) > 1" {
              }
              key "id";
              leaf id {
                type string;
              }
              uses neighbor-peer-group-grouping;
              uses neighbor-remote-as-grouping;
            }
          }
          list neighbor {
              description
                "Specify a neighbor router";
              must "count(*) > 1" {
              }
              key "id";
              leaf id {
                type inet:ip-address;
              }
              uses neighbor-peer-group-grouping;
              uses neighbor-remote-as-grouping;
          }
          container address-family {
            description
              "Enter Address Family command mode";
            // router bgp * / address-family ipv4 vrf
            uses address-family-no-vrf-grouping;
          }
        }
      }
    }
  }

  /////////////////////////////////////////////////////////
  // native / router / bgp
  /////////////////////////////////////////////////////////
  augment "/ios:native/ios:router" {
    uses config-bgp-grouping;
  }

    /////////////////////////////////////////////////////////
  // ip / community list
  /////////////////////////////////////////////////////////
  augment "/ios:native/ios:ip" {
    uses config-ip-community-list-grouping;
  }

  /////////////////////////////////////////////////////////
  // ip / extcommunity list
  /////////////////////////////////////////////////////////
  augment "/ios:native/ios:ip" {
    uses config-ip-extcommunity-list-grouping;
  }

  /////////////////////////////////////////////////////////
  // ip / as-path
  /////////////////////////////////////////////////////////
  augment "/ios:native/ios:ip/ios:as-path" {
    uses config-ip-as-path-grouping;
  }
}
